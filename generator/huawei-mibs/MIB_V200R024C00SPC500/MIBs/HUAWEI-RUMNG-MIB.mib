-- =================================================================
-- Copyright (C) 2023 by HUAWEI TECHNOLOGIES. All rights reserved.
-- Description: Remote unit management.
-- Reference:
-- Version: V1.11
--
-- =================================================================

    HUAWEI-RUMNG-MIB DEFINITIONS ::= BEGIN
        IMPORTS
            hwDatacomm
                FROM HUAWEI-MIB
            RowStatus
                FROM SNMPv2-TC
            IpAddress, Integer32, Unsigned32, Counter32, Counter64, OBJECT-TYPE, MODULE-IDENTITY, NOTIFICATION-TYPE
                FROM SNMPv2-SMI
             OBJECT-GROUP, MODULE-COMPLIANCE, NOTIFICATION-GROUP
                FROM SNMPv2-CONF;

        hwRuMngMIB MODULE-IDENTITY
            LAST-UPDATED "202312220000Z"
            ORGANIZATION "Huawei Technologies Co.,Ltd."
            CONTACT-INFO
                "Huawei Industrial Base
                  Bantian, Longgang
                   Shenzhen 518129
                   People's Republic of China
                   Website: http://www.huawei.com
                   Email: support@huawei.com
                "
            DESCRIPTION
                "Remote unit management.
                "

            -- Revision history
            REVISION    "202312220000Z"
            DESCRIPTION  "V1.11 modify the description of the hwRuCertMisMatch, hwRuCertMatch, hwRuMngDevConnectInterface, hwRuMngPortConnectInterface"

            REVISION    "202308230000Z"
            DESCRIPTION  "V1.10 modify the description of the hwRuMngDevMemoryUsage"

            REVISION    "202304070000Z"
            DESCRIPTION  "V1.09 add change hwRuMngPortMode type"

            REVISION    "202212270000Z"
            DESCRIPTION  "V1.08 add device information, port information and optical module information"

            REVISION    "202212150000Z"
            DESCRIPTION  "V1.07 add alarm about hwRuCertMisMatch"

            REVISION    "202209290000Z"
            DESCRIPTION  "V1.06 add alarm about UART"

            REVISION    "202207220000Z"
            DESCRIPTION  "V1.05 add alarm about mac usage"

            REVISION    "202203070000Z"
            DESCRIPTION  "V1.04 add alarm about authentication"

            REVISION    "202202190000Z"
            DESCRIPTION  "V1.03 add alarm about authentication"

            REVISION    "202201290000Z"
            DESCRIPTION  "V1.02 change hwRuMngRu  to hwRuMngRuEsn  "

            REVISION    "202107160000Z"
            DESCRIPTION  "V1.0 Initial version"
            ::= { hwDatacomm 667 }
--
-- Textual conventions
--
--
-- Node definitions
--
       hwRuMngTrapsVbOids OBJECT IDENTIFIER ::= { hwRuMngMIB 1 }
        hwRuMngRuEsn  OBJECT-TYPE
            SYNTAX OCTET STRING (SIZE (0..128))
            MAX-ACCESS accessible-for-notify
            STATUS current
            DESCRIPTION
                "The ESN of remote unit."
            ::= { hwRuMngTrapsVbOids 1 }  

        hwRuMngRuPortName OBJECT-TYPE
            SYNTAX OCTET STRING (SIZE (0..128))
            MAX-ACCESS accessible-for-notify
            STATUS current
            DESCRIPTION
                "The portid of remote unit."
            ::= { hwRuMngTrapsVbOids 2 }

        hwRuMngRuLinkExceptionReason OBJECT-TYPE
            SYNTAX OCTET STRING (SIZE (0..128))
            MAX-ACCESS accessible-for-notify
            STATUS current
            DESCRIPTION
                "The reason of remote unit exception."
            ::= { hwRuMngTrapsVbOids 3 }
        hwRuMngPortName OBJECT-TYPE
            SYNTAX OCTET STRING (SIZE (0..128))
            MAX-ACCESS accessible-for-notify
            STATUS current
            DESCRIPTION
                "Port name of the central device."
            ::= { hwRuMngTrapsVbOids 4 }
        hwRuMngRuPortAdminStatus OBJECT-TYPE
            SYNTAX INTEGER {
                up(1),       -- ready to pass packets
                down(2)
            }
            MAX-ACCESS accessible-for-notify
            STATUS current
            DESCRIPTION
                "Indicates the administrative status of the remote unit port."
            ::= { hwRuMngTrapsVbOids 5 }
        hwRuMngRuPortOperStatus OBJECT-TYPE
            SYNTAX INTEGER {
                up(1),       -- ready to pass packets
                down(2)
            }
            MAX-ACCESS accessible-for-notify
            STATUS current
            DESCRIPTION
                "Operational status of the remote unit port."
            ::= { hwRuMngTrapsVbOids 6 }
        hwRuMngRuPortDiscardPkts OBJECT-TYPE
            SYNTAX Counter64
            MAX-ACCESS accessible-for-notify
            STATUS current
            DESCRIPTION
                "The number of packets discarded on the remote unit port."
            ::= { hwRuMngTrapsVbOids 7 }
        hwRuMngRuPortDiscardPktThreshold OBJECT-TYPE
            SYNTAX Integer32
            MAX-ACCESS accessible-for-notify
            STATUS current
            DESCRIPTION
                "Packet discard threshold during the configured interval.unit(packet)."
            ::= { hwRuMngTrapsVbOids 8 }	
        hwRuMngRuPortDiscardPktInterval OBJECT-TYPE
            SYNTAX Integer32
            MAX-ACCESS accessible-for-notify
            STATUS current
            DESCRIPTION
                "The detection interval of the discard packet."
            ::= { hwRuMngTrapsVbOids 9 }	
        hwRuMngRuPortCrcErrorPkts OBJECT-TYPE
            SYNTAX Counter64
            MAX-ACCESS accessible-for-notify
            STATUS current
            DESCRIPTION
                "The number of crc packets on the remote unit port."
            ::= { hwRuMngTrapsVbOids 10 }
        hwRuMngRuPortCrcErrorPktThreshold OBJECT-TYPE
            SYNTAX Integer32
            MAX-ACCESS accessible-for-notify
            STATUS current
            DESCRIPTION
                "Crc Packet threshold during the configured interval.unit(packet)."
            ::= { hwRuMngTrapsVbOids 11 }	
        hwRuMngRuPortCrcErrorPktInterval OBJECT-TYPE
            SYNTAX Integer32
            MAX-ACCESS accessible-for-notify
            STATUS current
            DESCRIPTION
                "The detection interval of the crc packet."
            ::= { hwRuMngTrapsVbOids 12 }	
        hwRuMngRuPortBandWidthUsage OBJECT-TYPE
            SYNTAX Integer32
            MAX-ACCESS accessible-for-notify
            STATUS current
            DESCRIPTION
                "The bandwidth usage on the remote unit port."
            ::= { hwRuMngTrapsVbOids 13 }
        hwRuMngRuPortBandWidthUsageThreshold OBJECT-TYPE
            SYNTAX Integer32
            MAX-ACCESS accessible-for-notify
            STATUS current
            DESCRIPTION
                "The bandwidth usage threshold during the configured interval.unit(packet)."
            ::= { hwRuMngTrapsVbOids 14 }		
        hwRuMngRuPortOpticalAbnormalReason OBJECT-TYPE
            SYNTAX OCTET STRING (SIZE (0..128))
            MAX-ACCESS accessible-for-notify
            STATUS current
            DESCRIPTION
                "The reason of remote unit port optical module exception."
            ::= { hwRuMngTrapsVbOids 15 }
        hwRuMngRuSpec OBJECT-TYPE
            SYNTAX Integer32
            MAX-ACCESS accessible-for-notify
            STATUS current
            DESCRIPTION
                "The max number of the remote unit."
            ::= { hwRuMngTrapsVbOids 16 }
            
        hwRuMngFirmware OBJECT-TYPE
            SYNTAX OCTET STRING (SIZE (0..128))
            MAX-ACCESS accessible-for-notify
            STATUS current
            DESCRIPTION
                "The firmware type of remote-unit."
            ::= { hwRuMngTrapsVbOids 17 }
            
        hwRuMngFailReason OBJECT-TYPE
            SYNTAX OCTET STRING (SIZE (0..128))
            MAX-ACCESS accessible-for-notify
            STATUS current
            DESCRIPTION
                "The Reason for the remote unit upgrade failure."
            ::= { hwRuMngTrapsVbOids 18 } 
            
        hwRuMngPortRuSpec OBJECT-TYPE
            SYNTAX Integer32
            MAX-ACCESS accessible-for-notify
            STATUS current
            DESCRIPTION
                "The maximum number of remote units supported on a port."
            ::= { hwRuMngTrapsVbOids 19 }            

        hwRuMngOfflineReason OBJECT-TYPE
            SYNTAX OCTET STRING (SIZE (0..128))
            MAX-ACCESS accessible-for-notify
            STATUS current
            DESCRIPTION
                "The Reason for the remote offline."
            ::= { hwRuMngTrapsVbOids 20 }

        hwRuMngPseV33AbnReason OBJECT-TYPE
            SYNTAX OCTET STRING (SIZE (0..128))
            MAX-ACCESS accessible-for-notify
            STATUS current
            DESCRIPTION
                "The Reason for the remote unit PSE V33 abnormal."
            ::= { hwRuMngTrapsVbOids 21 }
        
        hwRuMngTempValue OBJECT-TYPE
            SYNTAX Integer32
            MAX-ACCESS accessible-for-notify
            STATUS current
            DESCRIPTION
                "The temperature of the remote unit."
            ::= { hwRuMngTrapsVbOids 22 }

        hwRuMngIICId OBJECT-TYPE
            SYNTAX Integer32
            MAX-ACCESS accessible-for-notify
            STATUS current
            DESCRIPTION
                "The fault IIC id of the remote unit."
            ::= { hwRuMngTrapsVbOids 23 } 

        hwRuMngIICName OBJECT-TYPE
        SYNTAX OCTET STRING (SIZE (0..128))
            MAX-ACCESS accessible-for-notify
            STATUS current
            DESCRIPTION
                "The fault IIC name of the remote unit."
            ::= { hwRuMngTrapsVbOids 24 }

        hwRuMngMacUsage OBJECT-TYPE
        SYNTAX Integer32
            MAX-ACCESS accessible-for-notify
            STATUS current
            DESCRIPTION
                "MAC address usage."
            ::= { hwRuMngTrapsVbOids 25 }

        hwRuMngMacThreshold OBJECT-TYPE
        SYNTAX Integer32
            MAX-ACCESS accessible-for-notify
            STATUS current
            DESCRIPTION
                "MAC address usage alarm threshold."
            ::= { hwRuMngTrapsVbOids 26 }


       hwRuMngTraps OBJECT IDENTIFIER ::= { hwRuMngMIB 2 }
        hwRuMngRuLinkAbnormal NOTIFICATION-TYPE
            OBJECTS { hwRuMngRuEsn, hwRuMngPortName, hwRuMngRuLinkExceptionReason }
            STATUS current
            DESCRIPTION
                "This notification is generated when remote unit connection is abnormal."
            ::= { hwRuMngTraps 1 }

        hwRuMngRuLinkNormal NOTIFICATION-TYPE
            OBJECTS { hwRuMngRuEsn, hwRuMngPortName, hwRuMngRuLinkExceptionReason }
            STATUS current
            DESCRIPTION
                "This notification is generated when remote unit connection is normal."
            ::= { hwRuMngTraps 2 }

        hwRuMngRuPortLinkDown NOTIFICATION-TYPE
            OBJECTS { hwRuMngRuEsn, hwRuMngRuPortName, hwRuMngRuPortAdminStatus, hwRuMngRuPortOperStatus }
            STATUS current
            DESCRIPTION
                "This notification is generated when the port status of the remote unit changes to down."
            ::= { hwRuMngTraps 3 }

         hwRuMngRuPortLinkUp NOTIFICATION-TYPE
            OBJECTS { hwRuMngRuEsn, hwRuMngRuPortName, hwRuMngRuPortAdminStatus, hwRuMngRuPortOperStatus }
            STATUS current
            DESCRIPTION
                "This notification is generated when the port status of the remote unit changes to up."
            ::= { hwRuMngTraps 4 }

         hwRuPortInputDiscardNotice NOTIFICATION-TYPE
            OBJECTS { hwRuMngRuEsn, hwRuMngRuPortName, hwRuMngRuPortDiscardPkts, hwRuMngRuPortDiscardPktThreshold, hwRuMngRuPortDiscardPktInterval }
            STATUS current
            DESCRIPTION
                "This notification is generated when the remote unit interface input discard exceed the trap threshold."
            ::= { hwRuMngTraps 5 }

         hwRuPortOutputDiscardNotice NOTIFICATION-TYPE
            OBJECTS { hwRuMngRuEsn, hwRuMngRuPortName, hwRuMngRuPortDiscardPkts, hwRuMngRuPortDiscardPktThreshold, hwRuMngRuPortDiscardPktInterval }
            STATUS current
            DESCRIPTION
                "This notification is generated when the remote unit interface output discard exceed the trap threshold."
            ::= { hwRuMngTraps 7 }

         hwRuPortCrcErrorRising NOTIFICATION-TYPE
            OBJECTS { hwRuMngRuEsn, hwRuMngRuPortName, hwRuMngRuPortCrcErrorPkts, hwRuMngRuPortCrcErrorPktThreshold, hwRuMngRuPortCrcErrorPktInterval }
            STATUS current
            DESCRIPTION
                "This notification is generated when the remote unit port CRC error is rising."
            ::= { hwRuMngTraps 9 }

         hwRuPortCrcErrorResume NOTIFICATION-TYPE
            OBJECTS { hwRuMngRuEsn, hwRuMngRuPortName, hwRuMngRuPortCrcErrorPkts, hwRuMngRuPortCrcErrorPktThreshold, hwRuMngRuPortCrcErrorPktInterval }
            STATUS current
            DESCRIPTION
                "This notification is generated when the remote unit port CRC error resume."
            ::= { hwRuMngTraps 10 }	

         hwRuPortInputRateRising NOTIFICATION-TYPE
            OBJECTS { hwRuMngRuEsn, hwRuMngRuPortName, hwRuMngRuPortBandWidthUsage, hwRuMngRuPortBandWidthUsageThreshold }
            STATUS current
            DESCRIPTION
                "This notification is generated when the remote unit interface input flow bandwidth usage exceeded the trap threshod."
            ::= { hwRuMngTraps 11 }

         hwRuPortInputRateResume NOTIFICATION-TYPE
            OBJECTS { hwRuMngRuEsn, hwRuMngRuPortName, hwRuMngRuPortBandWidthUsage, hwRuMngRuPortBandWidthUsageThreshold }
            STATUS current
            DESCRIPTION
                "This notification is generated when the remote unit interface input flow bandwidth usage was restored to the trap threshold."
            ::= { hwRuMngTraps 12 }

         hwRuPortOutputRateRising NOTIFICATION-TYPE
            OBJECTS { hwRuMngRuEsn, hwRuMngRuPortName, hwRuMngRuPortBandWidthUsage, hwRuMngRuPortBandWidthUsageThreshold }
            STATUS current
            DESCRIPTION
                "This notification is generated when the remote unit interface output flow bandwidth usage exceeded the trap threshod."
            ::= { hwRuMngTraps 13 }

         hwRuPortOutputRateResume NOTIFICATION-TYPE
            OBJECTS { hwRuMngRuEsn, hwRuMngRuPortName, hwRuMngRuPortBandWidthUsage, hwRuMngRuPortBandWidthUsageThreshold }
            STATUS current
            DESCRIPTION
                "This notification is generated when the remote unit interface output flow bandwidth usage was restored to the trap threshold."
            ::= { hwRuMngTraps 14 }

         hwRuPortOpticalPowerAbnormal NOTIFICATION-TYPE
            OBJECTS { hwRuMngRuEsn, hwRuMngRuPortName, hwRuMngRuPortOpticalAbnormalReason }
            STATUS current
            DESCRIPTION
                "This notification is generated when the remote unit interface optical module power is abnormal."
            ::= { hwRuMngTraps 15 }

         hwRuPortOpticalPowerResume NOTIFICATION-TYPE
            OBJECTS { hwRuMngRuEsn, hwRuMngRuPortName, hwRuMngRuPortOpticalAbnormalReason }
            STATUS current
            DESCRIPTION
                "This notification is generated when the remote unit interface recovered from power abnormal."
            ::= { hwRuMngTraps 16 }

         hwRuMngDevFull NOTIFICATION-TYPE
            OBJECTS { hwRuMngRuEsn, hwRuMngRuSpec }
            STATUS current
            DESCRIPTION
                "This notification is generated when the number of remote unit is overspec."
            ::= { hwRuMngTraps 17 }
            
         hwRuMngFirmwareUpdateFail NOTIFICATION-TYPE
            OBJECTS { hwRuMngRuEsn, hwRuMngPortName, hwRuMngFirmware, hwRuMngFailReason }
            STATUS current
            DESCRIPTION
                "The notification is generated when the remote unit firmware upgrade failed."
            ::= { hwRuMngTraps 19 }

         hwRuMngPortRuFull NOTIFICATION-TYPE   
            OBJECTS { hwRuMngPortName, hwRuMngRuEsn, hwRuMngPortRuSpec}
            STATUS current
            DESCRIPTION
                "This notification is generated when the number of remote units connected to ETH-Trunk exceeds the upper limit."
            ::= { hwRuMngTraps 21 }

         hwRuMngOnline NOTIFICATION-TYPE   
            OBJECTS { hwRuMngRuEsn, hwRuMngPortName}
            STATUS current
            DESCRIPTION
                "This notification is generated when the remote unit goes online."
            ::= { hwRuMngTraps 23 }

        hwRuMngOffline NOTIFICATION-TYPE   
            OBJECTS { hwRuMngRuEsn, hwRuMngPortName, hwRuMngOfflineReason}
            STATUS current
            DESCRIPTION
                "This notification is generated when the remote unit goes offline."
            ::= { hwRuMngTraps 25 }

        hwRuPseV33Abnormal NOTIFICATION-TYPE   
            OBJECTS { hwRuMngRuEsn, hwRuMngPseV33AbnReason}
            STATUS current
            DESCRIPTION
                "This notification is generated when the remote unit pse v33 is abnormal."
            ::= { hwRuMngTraps 27 }

        hwRuPseV33Resume NOTIFICATION-TYPE   
            OBJECTS { hwRuMngRuEsn }
            STATUS current
            DESCRIPTION
                "This notification is generated when the remote unit pse v33 goes normal."
            ::= { hwRuMngTraps 28 }

        hwRuPsePowerStatAbnormal NOTIFICATION-TYPE   
            OBJECTS { hwRuMngRuEsn}
            STATUS current
            DESCRIPTION
                "This notification is generated when the remote unit pse power supply is abnormal."
            ::= { hwRuMngTraps 29 }

        hwRuPsePowerStatResume NOTIFICATION-TYPE   
            OBJECTS { hwRuMngRuEsn }
            STATUS current
            DESCRIPTION
                "This notification is generated when the remote unit pse power supply goes normal."
            ::= { hwRuMngTraps 30 }

        hwRuTemperatureAbnormal NOTIFICATION-TYPE   
            OBJECTS { hwRuMngRuEsn, hwRuMngTempValue }
            STATUS current
            DESCRIPTION
                "This notification is generated when the remote unit temperature is abnormal."
            ::= { hwRuMngTraps 31 }

        hwRuTemperatureResume NOTIFICATION-TYPE   
            OBJECTS { hwRuMngRuEsn, hwRuMngTempValue }
            STATUS current
            DESCRIPTION
                "This notification is generated when the remote unit temperature goes normal."
            ::= { hwRuMngTraps 32 }

        hwRuPhyStatAbnormal NOTIFICATION-TYPE   
            OBJECTS { hwRuMngRuEsn }
            STATUS current
            DESCRIPTION
                "This notification is generated when the remote unit phy status is abnormal."
            ::= { hwRuMngTraps 33 }

        hwRuPhyStatResume NOTIFICATION-TYPE   
            OBJECTS { hwRuMngRuEsn }
            STATUS current
            DESCRIPTION
                "This notification is generated when the remote unit phy status goes normal."
            ::= { hwRuMngTraps 34 }

        hwRuIICFault NOTIFICATION-TYPE   
            OBJECTS { hwRuMngRuEsn, hwRuMngIICId, hwRuMngIICName}
            STATUS current
            DESCRIPTION
                "This notification is generated when the remote unit IIC fault."
            ::= { hwRuMngTraps 35 }

        hwRuAuthFail NOTIFICATION-TYPE   
            OBJECTS { hwRuMngRuEsn }
            STATUS current
            DESCRIPTION
                "This notification is generated the authentication to the remote unit failed."
            ::= { hwRuMngTraps 37 }

        hwRuAuthSuccess NOTIFICATION-TYPE   
            OBJECTS { hwRuMngRuEsn }
            STATUS current
            DESCRIPTION
                "This notification is generated the authentication to the remote unit succeeded."
            ::= { hwRuMngTraps 38 }

        hwRuPortCongestAlarm NOTIFICATION-TYPE
            OBJECTS { hwRuMngRuEsn, hwRuMngRuPortName }
            STATUS current
            DESCRIPTION
                "This notification is generated when the remote unit interface is congested."
            ::= { hwRuMngTraps 39 }

        hwRuPortCongestResume NOTIFICATION-TYPE
            OBJECTS { hwRuMngRuEsn, hwRuMngRuPortName }
            STATUS current
            DESCRIPTION
                "This notification is generated when the congestion on the remote unit interface is cleared."
            ::= { hwRuMngTraps 40 }

        hwRuMacUsageRaising NOTIFICATION-TYPE
            OBJECTS { hwRuMngRuEsn, hwRuMngMacUsage, hwRuMngMacThreshold }
            STATUS current
            DESCRIPTION
                "This notification is generated when MAC address usage exceeds the threshold alarm."
            ::= { hwRuMngTraps 41 }

        hwRuMacUsageFalling NOTIFICATION-TYPE
            OBJECTS { hwRuMngRuEsn, hwRuMngMacUsage, hwRuMngMacThreshold }
            STATUS current
            DESCRIPTION
                "This notification is generated when The MAC address usage rate is lower than the recovery alarm threshold."
            ::= { hwRuMngTraps 42 }

        hwRuUartStatAbnormal NOTIFICATION-TYPE   
            OBJECTS { hwRuMngRuEsn}
            STATUS current
            DESCRIPTION
                "This notification is generated when the remote unit UART communication is abnormal."
            ::= { hwRuMngTraps 43 }

        hwRuUartStatResume NOTIFICATION-TYPE   
            OBJECTS { hwRuMngRuEsn }
            STATUS current
            DESCRIPTION
                "This notification is generated when the remote unit UART communication goes normal."
            ::= { hwRuMngTraps 44 }

        hwRuCertMisMatch NOTIFICATION-TYPE   
            OBJECTS { hwRuMngRuEsn }
            STATUS current
            DESCRIPTION
                "This notification is generated the remote unit certificate version does not match the central device."
            ::= { hwRuMngTraps 45}

        hwRuCertMatch NOTIFICATION-TYPE   
            OBJECTS { hwRuMngRuEsn }
            STATUS current
            DESCRIPTION
                "This notification is generated the RU certificate version match the central device."
            ::= { hwRuMngTraps 46}

	
          hwRuMngConformance OBJECT IDENTIFIER ::= { hwRuMngMIB 3 }
            hwRuMngCompliances OBJECT IDENTIFIER ::= { hwRuMngConformance 1 }
            hwRuMngFullCompliance MODULE-COMPLIANCE
                STATUS current
                DESCRIPTION
                    "hwRuMngFullCompliance"
                MODULE 
                    MANDATORY-GROUPS { hwRuMngVbGrops, hwRuMngTrapGroup }
                ::= { hwRuMngCompliances 1 }

            hwRuMngGroups OBJECT IDENTIFIER ::= { hwRuMngConformance 2 }
              hwRuMngVbGrops OBJECT-GROUP
                  OBJECTS { hwRuMngRuEsn, hwRuMngRuPortName, hwRuMngRuLinkExceptionReason, hwRuMngPortName, hwRuMngRuPortAdminStatus, hwRuMngRuPortOperStatus,
                            hwRuMngRuPortDiscardPkts, hwRuMngRuPortDiscardPktThreshold, hwRuMngRuPortDiscardPktInterval, hwRuMngRuPortCrcErrorPkts, hwRuMngRuPortCrcErrorPktThreshold,
                            hwRuMngRuPortCrcErrorPktInterval, hwRuMngRuPortBandWidthUsage, hwRuMngRuPortBandWidthUsageThreshold, hwRuMngRuPortOpticalAbnormalReason, hwRuMngRuSpec, 
                            hwRuMngFirmware, hwRuMngFailReason, hwRuMngPortRuSpec, hwRuMngOfflineReason, hwRuMngPseV33AbnReason,  hwRuMngTempValue,
                            hwRuMngIICId, hwRuMngIICName, hwRuMngMacUsage, hwRuMngMacThreshold }
                STATUS current
                DESCRIPTION
                    "A collection of objects providing information about  remote unit."
                ::= {  hwRuMngGroups 1 }

              hwRuMngTrapGroup NOTIFICATION-GROUP
                  NOTIFICATIONS { hwRuMngRuLinkAbnormal, hwRuMngRuLinkNormal, hwRuMngRuPortLinkDown, hwRuMngRuPortLinkUp, hwRuPortInputDiscardNotice, hwRuPortOutputDiscardNotice, hwRuPortCrcErrorRising,
                  hwRuPortCrcErrorResume, hwRuPortInputRateRising, hwRuPortInputRateResume, hwRuPortOutputRateRising, hwRuPortOutputRateResume,
                  hwRuPortOpticalPowerAbnormal, hwRuPortOpticalPowerResume, hwRuMngDevFull, hwRuMngFirmwareUpdateFail, hwRuMngPortRuFull, hwRuMngOnline, hwRuMngOffline,
                  hwRuPseV33Abnormal, hwRuPseV33Resume, hwRuPsePowerStatAbnormal, hwRuPsePowerStatResume, hwRuTemperatureAbnormal, hwRuTemperatureResume, hwRuPhyStatAbnormal,
                  hwRuPhyStatResume, hwRuIICFault, hwRuAuthFail, hwRuAuthSuccess, hwRuPortCongestAlarm, hwRuPortCongestResume, hwRuMacUsageRaising, hwRuMacUsageFalling, hwRuUartStatAbnormal,
                 hwRuUartStatResume, hwRuCertMisMatch, hwRuCertMatch }
                STATUS current
                DESCRIPTION
                    "The trap enable group."
                ::= {  hwRuMngGroups 2 }

        hwRuMngDevTable OBJECT-TYPE
            SYNTAX SEQUENCE OF HwRuMngDevEntry
            MAX-ACCESS not-accessible
            STATUS current
            DESCRIPTION
                "The basic device information about remote unit."
            ::= { hwRuMngMIB 4 }

        hwRuMngDevEntry OBJECT-TYPE
            SYNTAX HwRuMngDevEntry
            MAX-ACCESS not-accessible
            STATUS current
            DESCRIPTION
                "The basic device information about remote unit."
            INDEX { hwRuMngDevEsn }
            ::= { hwRuMngDevTable 1 }

        HwRuMngDevEntry ::=
            SEQUENCE { 
                    hwRuMngDevEsn
                        OCTET STRING,
                    hwRuMngDevStatus
                        INTEGER,
                    hwRuMngDevMemoryUsage
                        Integer32,
                    hwRuMngDevName
                        OCTET STRING,
                    hwRuMngDevType
                        OCTET STRING,
                    hwRuMngDevOnlineTime
                        Integer32,
                    hwRuMngDevConnectInterface
                        OCTET STRING,
                    hwRuMngDevAbnormalReason
                        OCTET STRING,
                    hwRuMngDevSlotIndex
                        Integer32,
                    hwRuMngDevAppVersion
                        OCTET STRING
                }

            hwRuMngDevEsn OBJECT-TYPE
                SYNTAX OCTET STRING (SIZE(1..128))
                MAX-ACCESS read-only
                STATUS current
                DESCRIPTION
                    "The ESN of an RU. It uniquely identifies an RU."
                ::= { hwRuMngDevEntry 1 }

            hwRuMngDevStatus OBJECT-TYPE
                SYNTAX INTEGER
                    {
                    normal(0),
                    upgrading(1),
                    idle(2),
                    abnormal(3),
                    configuring(4)
                    }
                MAX-ACCESS read-only
                STATUS current
                DESCRIPTION
                    "The device status."
                ::= { hwRuMngDevEntry 2 }

            hwRuMngDevMemoryUsage OBJECT-TYPE
                SYNTAX Integer32 (0..100)
                MAX-ACCESS read-only
                STATUS current
                DESCRIPTION
                    "The memory usage of an RU."
                ::= { hwRuMngDevEntry 3 }

            hwRuMngDevName OBJECT-TYPE
                SYNTAX OCTET STRING (SIZE(1..128))
                MAX-ACCESS read-only
                STATUS current
                DESCRIPTION
                    "The alias of an RU."
                ::= { hwRuMngDevEntry 4 }

            hwRuMngDevType OBJECT-TYPE
                SYNTAX OCTET STRING (SIZE(1..128))
                MAX-ACCESS read-only
                STATUS current
                DESCRIPTION
                    "The model of an RU."
                ::= { hwRuMngDevEntry 5 }

            hwRuMngDevOnlineTime OBJECT-TYPE
                SYNTAX Integer32
                MAX-ACCESS read-only
                STATUS current
                DESCRIPTION
                    "The time when an RU goes online."
                ::= { hwRuMngDevEntry 6 }

            hwRuMngDevConnectInterface OBJECT-TYPE
                SYNTAX OCTET STRING (SIZE(1..128))
                MAX-ACCESS read-only
                STATUS current
                DESCRIPTION
                    "The interface connecting the RU to the central device."
                ::= { hwRuMngDevEntry 7 }

            hwRuMngDevAbnormalReason OBJECT-TYPE
                SYNTAX OCTET STRING (SIZE(1..128))
                MAX-ACCESS read-only
                STATUS current
                DESCRIPTION
                    "The cause of an RU exception."
                ::= { hwRuMngDevEntry 8 }

            hwRuMngDevSlotIndex OBJECT-TYPE
                SYNTAX Integer32
                MAX-ACCESS read-only
                STATUS current
                DESCRIPTION
                    "The virtual slot number of an RU."
                ::= { hwRuMngDevEntry 9 }

            hwRuMngDevAppVersion OBJECT-TYPE
                SYNTAX OCTET STRING (SIZE(1..128))
                MAX-ACCESS read-only
                STATUS current
                DESCRIPTION
                    "The version number of an RU."
                ::= { hwRuMngDevEntry 10 }

        hwRuMngPortTable OBJECT-TYPE
            SYNTAX SEQUENCE OF HwRuMngPortEntry
            MAX-ACCESS not-accessible
            STATUS current
            DESCRIPTION
                "The basic port information about remote unit."
            ::= { hwRuMngMIB 5 }

        hwRuMngPortEntry OBJECT-TYPE
            SYNTAX HwRuMngPortEntry
            MAX-ACCESS not-accessible
            STATUS current
            DESCRIPTION
                "The basic port information about remote unit."
            INDEX { hwRuMngPortEsn, hwRuMngPortIndex }
            ::= { hwRuMngPortTable 1 }

        HwRuMngPortEntry ::=
            SEQUENCE { 
                    hwRuMngPortEsn
                        OCTET STRING,
                    hwRuMngPortIndex
                        Integer32,
                    hwRuMngPortStatus
                        INTEGER,
                    hwRuMngPortInputRate
                        Counter64,
                    hwRuMngPortOutputRate
                        Counter64,
                    hwRuMngPortInputPeakRate
                        Counter64,
                    hwRuMngPortOutputPeakRate
                        Counter64,
                    hwRuMngPortInputTraffic
                        Counter64,
                    hwRuMngPortOutputTraffic
                        Counter64,
                    hwRuMngPortRuName
                        OCTET STRING,
                    hwRuMngPortMode
                        Integer32,
                    hwRuMngPortPhyStatus
                        Integer32,
                    hwRuMngPortAdminStatus
                        Integer32,
                    hwRuMngPortAutoNegotiation
                        Integer32,
                    hwRuMngPortDuplex
                        Integer32,
                    hwRuMngPortSpeed
                        Integer32,
                    hwRuMngPortTrunkName
                        OCTET STRING,
                    hwRuMngPortConnectInterface
                        OCTET STRING
                }

            hwRuMngPortEsn OBJECT-TYPE
                SYNTAX OCTET STRING (SIZE(1..128))
                MAX-ACCESS read-only
                STATUS current
                DESCRIPTION
                    "The ESN of an RU. It uniquely identifies an RU."
                ::= { hwRuMngPortEntry 1 }

            hwRuMngPortIndex OBJECT-TYPE
                SYNTAX Integer32 (0..100)
                MAX-ACCESS read-only
                STATUS current
                DESCRIPTION
                    "The port index."
                ::= { hwRuMngPortEntry 2 }

            hwRuMngPortStatus OBJECT-TYPE
                SYNTAX INTEGER
                    {
                    down(1),
                    up(2)
                    }
                MAX-ACCESS read-only
                STATUS current
                DESCRIPTION
                    "The current running status of a port."
                ::= { hwRuMngPortEntry 3 }

            hwRuMngPortInputRate OBJECT-TYPE
                SYNTAX Counter64
                MAX-ACCESS read-only
                STATUS current
                DESCRIPTION
                    "The inbound rate of a port, in bit/s. The value is the average value in the latest statistical period."
                ::= { hwRuMngPortEntry 4 }

            hwRuMngPortOutputRate OBJECT-TYPE
                SYNTAX Counter64
                MAX-ACCESS read-only
                STATUS current
                DESCRIPTION
                    "The outbound rate of a port, in bit/s. The value is the average value in the latest statistical period."
                ::= { hwRuMngPortEntry 5 }

            hwRuMngPortInputPeakRate OBJECT-TYPE
                SYNTAX Counter64
                MAX-ACCESS read-only
                STATUS current
                DESCRIPTION
                    "The peak rate of incoming traffic on a port, in bit/s. The value is the peak rate in the latest statistical period."
                ::= { hwRuMngPortEntry 6 }

            hwRuMngPortOutputPeakRate OBJECT-TYPE
                SYNTAX Counter64
                MAX-ACCESS read-only
                STATUS current
                DESCRIPTION
                    "The peak rate of outgoing traffic on a port, in bit/s. The value is the peak rate in the latest statistical period."
                ::= { hwRuMngPortEntry 7 }

            hwRuMngPortInputTraffic OBJECT-TYPE
                SYNTAX Counter64
                MAX-ACCESS read-only
                STATUS current
                DESCRIPTION
                    "The incoming traffic statistics on a port, which is the incremental value within a collection period, in bytes."
                ::= { hwRuMngPortEntry 8 }

            hwRuMngPortOutputTraffic OBJECT-TYPE
                SYNTAX Counter64
                MAX-ACCESS read-only
                STATUS current
                DESCRIPTION
                    "The outgoing traffic statistics on a port, which is the incremental value within a collection period, in bytes."
                ::= { hwRuMngPortEntry 9 }

            hwRuMngPortRuName OBJECT-TYPE
                SYNTAX OCTET STRING (SIZE(1..128))
                MAX-ACCESS read-only
                STATUS current
                DESCRIPTION
                    "The port name."
                ::= { hwRuMngPortEntry 10 }

            hwRuMngPortMode OBJECT-TYPE
                SYNTAX Integer32
                MAX-ACCESS read-only
                STATUS current
                DESCRIPTION
                    "The port mode."
                ::= { hwRuMngPortEntry 11 }
 
            hwRuMngPortPhyStatus OBJECT-TYPE
                SYNTAX Integer32
                MAX-ACCESS read-only
                STATUS current
                DESCRIPTION
                    "The PHY status of an RU port."
                ::= { hwRuMngPortEntry 12 }
 
            hwRuMngPortAdminStatus OBJECT-TYPE
                SYNTAX Integer32
                MAX-ACCESS read-only
                STATUS current
                DESCRIPTION
                    "The administrative status of an RU port."
                ::= { hwRuMngPortEntry 13 }
            hwRuMngPortAutoNegotiation OBJECT-TYPE
                SYNTAX Integer32
                MAX-ACCESS read-only
                STATUS current
                DESCRIPTION
                    "The auto-negotiation status of an RU port."
                ::= { hwRuMngPortEntry 14 }
            hwRuMngPortDuplex OBJECT-TYPE
                SYNTAX Integer32
                MAX-ACCESS read-only
                STATUS current
                DESCRIPTION
                    "The duplex status of an RU port."
                ::= { hwRuMngPortEntry 15 }
            hwRuMngPortSpeed OBJECT-TYPE
                SYNTAX Integer32
                MAX-ACCESS read-only
                STATUS current
                DESCRIPTION
                    "The rate at which an RU port works."
                ::= { hwRuMngPortEntry 16 }
            hwRuMngPortTrunkName OBJECT-TYPE
                SYNTAX OCTET STRING (SIZE(1..128))
                MAX-ACCESS read-only
                STATUS current
                DESCRIPTION
                    "The name of the Eth-Trunk port to which an RU interface is added."
                ::= { hwRuMngPortEntry 17 }
            hwRuMngPortConnectInterface OBJECT-TYPE
                SYNTAX OCTET STRING (SIZE(1..128))
                MAX-ACCESS read-only
                STATUS current
                DESCRIPTION
                    "The physical interface connecting the RU to the central device."
                ::= { hwRuMngPortEntry 18 }

        hwRuMngSfpTable OBJECT-TYPE
            SYNTAX SEQUENCE OF HwRuMngSfpEntry
            MAX-ACCESS not-accessible
            STATUS current
            DESCRIPTION
                "Basic information about the optical module."
            ::= { hwRuMngMIB 6 }
 
        hwRuMngSfpEntry OBJECT-TYPE
            SYNTAX HwRuMngSfpEntry
            MAX-ACCESS not-accessible
            STATUS current
            DESCRIPTION
                "Basic information about the optical module."
            INDEX { hwRuMngSfpEsn, hwRuMngSfpIndex }
            ::= { hwRuMngSfpTable 1 }

        HwRuMngSfpEntry ::=
            SEQUENCE { 
                    hwRuMngSfpEsn
                        OCTET STRING,
                    hwRuMngSfpIndex
                        Integer32,
                    hwRuMngSfpName
                        OCTET STRING,
                    hwRuMngSfpCertified
                        Integer32,
                    hwRuMngSfpManuDate
                        OCTET STRING,
                    hwRuMngSfpBandwidth
                        Integer32,
                    hwRuMngSfpSerialNumber
                        OCTET STRING,
                    hwRuMngSfpTransferDistance
                        OCTET STRING,
                    hwRuMngSfpSupportDdm
                        Integer32,
                    hwRuMngSfpTemperature
                        OCTET STRING,
                    hwRuMngSfpTempHighThreshold
                        OCTET STRING,
                    hwRuMngSfpTempLowThreshold
                        OCTET STRING,
                    hwRuMngSfpVoltage
                        OCTET STRING,
                    hwRuMngSfpTransceiverType
                        OCTET STRING,
                    hwRuMngSfpVendorName
                        OCTET STRING,
                    hwRuMngSfpTransferMode
                        Integer32
                }

            hwRuMngSfpEsn OBJECT-TYPE
                SYNTAX OCTET STRING (SIZE(1..128))
                MAX-ACCESS read-only
                STATUS current
                DESCRIPTION
                    "The ESN of an RU. It uniquely identifies an RU."
                ::= { hwRuMngSfpEntry 1 }

            hwRuMngSfpIndex OBJECT-TYPE
                SYNTAX Integer32 (0..100)
                MAX-ACCESS read-only
                STATUS current
                DESCRIPTION
                    "The port index."
                ::= { hwRuMngSfpEntry 2 }

            hwRuMngSfpName OBJECT-TYPE
                SYNTAX OCTET STRING (SIZE(1..128))
                MAX-ACCESS read-only
                STATUS current
                DESCRIPTION
                    "The port name."
                ::= { hwRuMngSfpEntry 3 }

            hwRuMngSfpCertified OBJECT-TYPE
                SYNTAX Integer32
                MAX-ACCESS read-only
                STATUS current
                DESCRIPTION
                    "Whether an optical module is non-certified."
                ::= { hwRuMngSfpEntry 4 }
 
            hwRuMngSfpManuDate OBJECT-TYPE
                SYNTAX OCTET STRING (SIZE(1..128))
                MAX-ACCESS read-only
                STATUS current
                DESCRIPTION
                    "The manufacturing date of an optical module."
                ::= { hwRuMngSfpEntry 5 }
 
            hwRuMngSfpBandwidth OBJECT-TYPE
                SYNTAX Integer32
                MAX-ACCESS read-only
                STATUS current
                DESCRIPTION
                    "The bandwidth of an optical module, in Mbits/s."
                ::= { hwRuMngSfpEntry 6 }
 
            hwRuMngSfpSerialNumber OBJECT-TYPE
                SYNTAX OCTET STRING (SIZE(1..128))
                MAX-ACCESS read-only
                STATUS current
                DESCRIPTION
                    "The SN of an optical module."
                ::= { hwRuMngSfpEntry 7 }
 
            hwRuMngSfpTransferDistance OBJECT-TYPE
                SYNTAX OCTET STRING (SIZE(1..128))
                MAX-ACCESS read-only
                STATUS current
                DESCRIPTION
                    "The transmission distance description."
                ::= { hwRuMngSfpEntry 8 }
 
            hwRuMngSfpSupportDdm OBJECT-TYPE
                SYNTAX Integer32
                MAX-ACCESS read-only
                STATUS current
                DESCRIPTION
                    "whether DDM module diagnosis is supported."
                ::= { hwRuMngSfpEntry 9 }
 
            hwRuMngSfpTemperature OBJECT-TYPE
                SYNTAX OCTET STRING (SIZE(1..128))
                MAX-ACCESS read-only
                STATUS current
                DESCRIPTION
                    "The temperature of an optical module."
                ::= { hwRuMngSfpEntry 10 }
 
            hwRuMngSfpTempHighThreshold OBJECT-TYPE
                SYNTAX OCTET STRING (SIZE(1..128))
                MAX-ACCESS read-only
                STATUS current
                DESCRIPTION
                    "The upper temperature threshold of an optical module."
                ::= { hwRuMngSfpEntry 11 }
 
            hwRuMngSfpTempLowThreshold OBJECT-TYPE
                SYNTAX OCTET STRING (SIZE(1..128))
                MAX-ACCESS read-only
                STATUS current
                DESCRIPTION
                    "The lower temperature threshold of an optical module."
                ::= { hwRuMngSfpEntry 12 }
 
            hwRuMngSfpVoltage OBJECT-TYPE
                SYNTAX OCTET STRING (SIZE(1..128))
                MAX-ACCESS read-only
                STATUS current
                DESCRIPTION
                    "The voltage of an optical module, in V."
                ::= { hwRuMngSfpEntry 13 }
 
            hwRuMngSfpTransceiverType OBJECT-TYPE
                SYNTAX OCTET STRING (SIZE(1..128))
                MAX-ACCESS read-only
                STATUS current
                DESCRIPTION
                    "The type of an optical module."
                ::= { hwRuMngSfpEntry 14 }
 
            hwRuMngSfpVendorName OBJECT-TYPE
                SYNTAX OCTET STRING (SIZE(1..128))
                MAX-ACCESS read-only
                STATUS current
                DESCRIPTION
                    "The manufacturer of an optical module."
                ::= { hwRuMngSfpEntry 15 }
 
            hwRuMngSfpTransferMode OBJECT-TYPE
                SYNTAX Integer32
                MAX-ACCESS read-only
                STATUS current
                DESCRIPTION
                    "The transmission mode of an optical module:"
                ::= { hwRuMngSfpEntry 16 }
    END
--
-- HUAWEI-RUMNG-MIB.mib
--
