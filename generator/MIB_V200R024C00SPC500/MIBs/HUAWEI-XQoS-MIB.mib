-- =================================================================
-- Copyright (C) 2024 by  HUAWEI TECHNOLOGIES. All rights reserved
--
-- Description: This mib file is used for management of huawei Class Based
--              QoS information.
-- Reference:
-- Version: V4.00
-- History:
--              v1.0 tianli,2004.4.10,publish
--              v1.1
--                  modified by chengang
--                  modified by zhangwenwu
--                  modified by wanglili
--                  modified by hezhifeng
--                  modified by dongling
--                  modified by tongtingting
--              V2.18
--                  modified by chenlong
--              V2.19
--                  modified by suxunjin
--              v2.20
--                  modified by lixinzhuo
--              v2.21
--                  modified by liuxiaoyan
--              v2.22
--                  modified by jinxiaoyan
--              v2.23
--                  modified by wangjing
--              v2.24
--                  modified by renxiaoyuan
--              v2.25
--                  modified by jinxiaoyan
--              v2.26
--                  modified by lixinzhuo
--              v2.27
--                  modified by sunhongliang
--              v2.28
--                  modified by renxiaoyuan
--              v2.29
--                  modified by maruoyu
--              v2.30
--                  modified by renxiaoyuan
--              v2.31
--                  modified by luyanyan
--              V2.32
--                  modified by wangjing
--              V2.33
--                  modified by wangjing
--              V2.34
--                  modified by wangxiaoyan
--              V2.35
--                  modified by zhoushujie
--              V2.36
--                  modified by wangjing
--              V2.37
--                  modified by wangjing
--              V2.38
--                  modified by liuxiaoyan
--              V2.39
--                  modified by songjian
--              V2.40
--                  modified by magang
--              V2.41
--                  modified by chenlong
--              V2.42
--                  modified by magang
--              V2.43
--                  modified by chenlong
--              V2.44
--                  modified by chenhao
--              V2.45
--                  modified by liye
--              V2.46
--                  modified by wangzhe
--              V2.47
--                  modified by chenhao
--              V2.48
--                  modified by chenhao
--              V2.49
--                  modified by magang
--              V2.50
--                  modified by zhangjian
--              V2.51
--                  modified by magang
--              V2.52
--                  modified by dongyanan
--              V2.53
--                  modified by xuechenguang
--              V2.55
--                  modified by pengsheng
--              V2.57
--                  modified by zhangmingming
--              V2.58
--                  modified by xiejiale
--              V2.59
--                  modified by lizhen
--              V2.60
--                  modified by wangcheng
--              V2.61
--                  modified by liangyun
--              V2.62
--                  modified by wanghongke
--              V2.63
--                  modified by zhouzaihua
--              V2.64
--                  modified by sunqirui
--              V2.66
--                  modified by luhongyu
--              V2.67
--                  modified by guanjiazhi
--              V2.69
--                  modified by sunqirui
--              V2.70
--                  modified by chenxu
--              V2.71
--                  modified by yejun
--              V2.72
--                  modified by zhouzaihua
--              V2.73
--                  modified by chenxu
--              V2.73
--                  modified by guzhen
--              V2.75
--                  modified by lilei
--              V2.76
--                  modified by chenxu
--              V2.77
--                  modified by zhouzaihua
--              V2.79
--                  modified by wuyifan
--              V2.83
--                  modified by hehaiyan
--              V2.84
--                  modified by hanhongyun
--              V2.85
--                  modified by wuyifan
--              V2.86
--                  modified by zhouzaihua
--              V2.87
--                  modified by zhouzaihua
--              V2.88
--                  modified by liyuanze
--              V2.89
--                  modified by lidapeng
--              V2.90
--                  modified by luhongyu
--              V2.91
--                  modified by qilongfei
--              V2.92
--                  modified by guanqingyu
--              V2.93
--                  modified by xiejiayou
--              V2.94
--                  modified by zhouzaihua
--              V2.95
--                  modified by gaolikun
--              V2.97
--                  modified by yanghaopeng
--                  modified by libin
--                  modified by yangchengsi
--              V2.98
--                  modified by zhaomingzhe
--              V2.99
--                  modified by zhaoqingqing
--              V3.01
--                  modified by dongyanhong
--              V3.02
--                  modified by xuehui
--              V3.03
--                  modified by zhaoqingqing
--              V3.04
--                  modified by shenjiulong
--              V3.05
--                  modified by xuehui
--              V3.06
--                  modified by xuehui
--              V3.07
--                  modified by xuehui
--              V3.08
--                  modified by lihongling
--              V3.10
--                  modified by xuehui
--              V3.11
--                  modified by jiangruochen
--              V3.12
--                  modified by liuxu
--              V3.13
--                  modified by liuxu
--              V3.14
--                  modified by shenlin
--              V3.15
--                  modified by liuxu
--              V3.16
--                  modified by panchao
--              V3.18
--                  modified by zhengjinke
--              V3.19
--                  modified by xiaozhiguang
--              V3.20
--                  modified by chenting
--              V3.21
--                  modified by maoyingxia
--              V3.25
--                  modified by guohongbo
--              V3.26
--                  modified by wurui
--              V3.28
--                  modified by zhaoxing
--              V3.29
--                  modified by wurui
--              V3.32
--                  modified by shaoshiwen
--              V3.34
--                  modified by shaoshiwen
--              V3.36
--                  modified by gaozheng
--              V3.37
--                  modified by shaoshiwen
--              V3.38
--                  modified by yangting
--              V3.39
--                  modified by jiajian
--              V3.40
--                  modified by maoyingxia
--              V3.41
--                  modified by jiajian
--              V3.45
--                  modified by dujianghai
--              V3.46
--                  modified by wuyifan
--              V3.47
--                  modified by dongyanan
--              V3.49
--                  modified by qixin
--              V3.50
--                  modified by qixin
--              V3.51
--                  modified by wangjian
--              V3.52
--                  modified by wangjian
--              V3.53
--                  modified by chenlong
--              V3.56
--                  modified by qixin
--              V3.57
--                  modified by qiaojuyang
--              V3.58
--                  modified by qixin
--              V3.59
--                  modified by qixin
--              V3.60
--                  modified by mengxiangyu
--              V3.61
--                  modified by huangliang
--              V3.62
--                  modified by tanyashi
--              V3.63
--                  modified by qixin
--              V3.64
--                  modified by zhaobolun
--              V3.65
--                  modified by xiazijie
--              V3.66
--                  modified by tanyashi
--              V3.68
--                  modified by yanghao
--              V3.69
--                  modified by zhaohaoran
--              V3.70
--                  modified by qixin
--              V3.71
--                  modified by xiazijie
--              V3.73
--                  modified by zhaohaoran
--              V3.74
--                  modified by qixin
--              V3.75
--                  modified by qixin
--              V3.76
--                  modified by qixin
--              V3.79
--                  modified by qixin
--              V3.80
--                  modified by zhangjie
--              V3.81
--                  modified by yangying
--              V3.82
--                  modified by fangshiting
--              V3.83
--                  modified by wangzhiqiang
--              V3.84
--                  modified by fangshiting
--              V3.85
--                  modified by dongyanan
--              V3.86
--                  modified by wuhejia
--              V3.87
--                  modified by qixin
--              V3.88
--                  modified by qixin
--              V3.89
--                  modified by xiazijie
--              V3.91
--                  modified by xiazijie
--              V3.92
--                  modified by xiazijie
--              V3.97
--                  modified by yanghao
-- =================================================================

HUAWEI-XQoS-MIB DEFINITIONS ::= BEGIN

    IMPORTS
        hwDatacomm
            FROM HUAWEI-MIB
        EnabledStatus
            FROM P-BRIDGE-MIB
        InterfaceIndex
            FROM IF-MIB
        OBJECT-GROUP, MODULE-COMPLIANCE, NOTIFICATION-GROUP
            FROM SNMPv2-CONF
        Integer32, Counter32, Counter64, Unsigned32, IpAddress, TimeTicks, OBJECT-TYPE, MODULE-IDENTITY, NOTIFICATION-TYPE
            FROM SNMPv2-SMI
        RowStatus, MacAddress, TEXTUAL-CONVENTION
            FROM SNMPv2-TC
        hwQoS
            FROM HUAWEI-CBQOS-MIB;

    --BaType
    BaType ::= TEXTUAL-CONVENTION
        STATUS  current
        DESCRIPTION
            "The Direction Policy apply on."
        SYNTAX  INTEGER {
            vlan8021p (1),
            dscp (2),
            mplsExp(3),
            ipPri(4),
            hqosVlan8021p(5),
            hqosDscp(6),
            hqosMplsExp(7),
            hqosIpPri(8),
            vlan8021pInbound(9)
            }

    hwXQoSMIB MODULE-IDENTITY
        LAST-UPDATED  "202408142200Z"
        ORGANIZATION
            "Huawei Technologies Co.,Ltd."
        CONTACT-INFO
            "Huawei Industrial Base
              Bantian, Longgang
               Shenzhen 518129
               People's Republic of China
               Website: http://www.huawei.com
               Email: support@huawei.com
             "

        DESCRIPTION
            "MODULE-IDENTITY"
     --add by weimingcen
        REVISION "202408142200Z"
        DESCRIPTION
            "Add hwXQoSCpDefendChassisID."
     --add by xiazijie
        REVISION "202408022200Z"
        DESCRIPTION
            "Add hwXQoSBgpFlowspecDDoSLowPriorityAlarm, hwXQoSBgpFlowspecDDoSLowPriorityAlarmClear."
     --add by xiazijie
        REVISION "202406132200Z"
        DESCRIPTION
            "Del hwXQoSTrafficPolicyRuleResoucePreAlarmReasonDescription."
     --add by dulongkun
        REVISION "202406052200Z"
        DESCRIPTION
            "Add  hwXQoSUnsupportedFeatureAlarmFeatureType"
     --add by zhaohaoran
        REVISION "202405212200Z"
        DESCRIPTION
            "Add  hwXQoSBindingTrafficPolicyBasicResourceTable, hwXQoSBindingTrafficPolicyChassisBasicResourceTable"

     --add by chenlong
        REVISION "202405162128Z"
        DESCRIPTION
            "Add hwXQoSFLowMatrixRailInvalidAlarm, hwXQoSFLowMatrixRailInvalidAlarmResume"

     --add by xiazijie
        REVISION "202405081800Z"
        DESCRIPTION
            "Add  hwXQoSBgpFlowspecDestinationOriginAsOverIPv6Alarm, hwXQoSBgpFlowspecDestinationOriginAsOverIPv6AlarmClear, hwXQoSBgpFlowspecDestinationCommunityOverAlarm, hwXQoSBgpFlowspecDestinationCommunityOverAlarmClear, hwXQoSTrafficPolicyRuleResoucePreAlarm, hwXQoSTrafficPolicyRuleResoucePreAlarmResume"

	 --add by yanghao
       REVISION "202404011544Z"
        DESCRIPTION
            "Add hwXACLEPGGroupMemberMacAlarm"

     --add by xiazijie
        REVISION "202403251800Z"
        DESCRIPTION
            "Add  hwXQoSFlowspecNotSupportBoardEvent"

    --add by qixin
 	 	REVISION "202403131645Z"
 	 	DESCRIPTION
 	 	"Modify description of hwXQoSIfDiffDomainName"

    --add by qixin
 	 	REVISION "202402251214Z"
 	 	DESCRIPTION
 	 	"Modify description of hwXQoSIfDiffDomainTable and size of hwXQoSIfDiffDomainName"

	--add by wuhejia
        REVISION "202310071937Z"
        DESCRIPTION
            "Modify description of hwXQoSEcnStatTable"

	--add by dongyanan
        REVISION "202309181527Z"
        DESCRIPTION
            "Modify hwXQoSRedirectNextHopInvalidAlarm,hwXQoSRedirectNextHopLackResAlarm"

	--add by fangshiting
        REVISION "202309161434Z"
        DESCRIPTION
            "Modify hwXQoSPfcRateStatisticsObjects"

	--add by wangzhiqiang
        REVISION "202309091609Z"
        DESCRIPTION
            "Add hwXQosHeadRoomPoolApplyFailAlarm, hwXQosHeadRoomPoolApplyFailAlarmResume, hwXQosPfcBufferApplyFailAlarm, hwXQosPfcBufferApplyFailAlarmResume"

	--add by fangshiting
        REVISION "202309071958Z"
        DESCRIPTION
            "Add hwXQoSPfcRateStatisticsObjects"

	 --add by yangying
		REVISION "202308282109Z"
		DESCRIPTION
			"Fix hwXQoSChipBufferOverrun, hwXQoSChipBufferOverrunResume"

     --add by zhangjie
        REVISION "202308241100Z"
        DESCRIPTION
            "Add hwXQoSPfcRxRateAlarm, hwXQoSPfcRxRateResume, hwXQoSPfcTxRateAlarm, hwXQoSPfcTxRateResume."

     --add by yangying
        REVISION "202308052031Z"
        DESCRIPTION
            "Del hwXQoSInterfaceHQoSFailAlarmReasonDescription."

     --add by yangying
        REVISION "202307251049Z"
        DESCRIPTION
            "Add hwXQoSChipBufferOverrun, hwXQoSChipBufferOverrunResume, hwXQoSEcnStatisticsObjects."

     --add by gaolikun
        REVISION "202304232022Z"
        DESCRIPTION
            "Add hwXQoSAclTcamResShareUsedNumber."

     --add by qixin
        REVISION "202303290858Z"
        DESCRIPTION
            "Add  hwXQoSSlotTrafficCongestionAlarm"

     --add by qixin
        REVISION "202302152330Z"
        DESCRIPTION
            "Add  hwXQosBoardServiceMismatchEvent"

     --add by qixin
        REVISION "202302012018Z"
        DESCRIPTION
            "Add hwXQoSFwdResourceOverload, hwXQoSFwdResourceOverloadResume"

     --add by zhaohaoran
        REVISION "202212132201Z"
        DESCRIPTION
            "Delete useless comments"

     --add by suyibo
        REVISION "202211301655Z"
        DESCRIPTION
            "Add  hwXQoSCarPercent"

     --add by xiazijie
        REVISION "202211281132Z"
        DESCRIPTION
            "Add  hwXQoSReceivedMultiPauseFrameInterfaceDownAlarm, hwXQoSTrunkTrafficCongestionAlarm"

     --add by qixin
        REVISION "202209141422Z"
        DESCRIPTION
            "Add  hwXQoSBoardHQoSFailAlarm, hwXQoSInterfaceHQoSFailAlarm"

     --add by zhaohaoran
        REVISION "202207211154Z"
        DESCRIPTION
            "Modify  datatype of hwXQoSRedirectNextHopEventLogRdrType hwXQoSInterfaceDownRedirectNextHopInvalidAlarmRdrType to string"

     --add by yanghao
        REVISION "202207061539Z"
        DESCRIPTION
            "Add hwXACLEPGRuleAlarm hwXACLEPGRuleResume"

     --add by tanyashi
        REVISION "202205181538Z"
        DESCRIPTION
            "Modify  hwXQosCarResourceServiceType"

     --add by tanyashi
        REVISION "202204262216Z"
        DESCRIPTION
            "Modify  hwXQosCarResourceServiceType"

     --add by xiazijie
        REVISION "202204161537Z"
        DESCRIPTION
            "Add  hwXQoSModeChannelOverEthBnBwdAlarm,hwXQoSModeChannelOverEthBnBwdResume"

     --add by zhaobolun
        REVISION "202201291420Z"
        DESCRIPTION
            "Modify  hwXQoSCarBindwidthExceedChipLimitAlarm,hwXQoSCarBindwidthExceedChipLimitResume"

     --add by qixin
        REVISION "202201261200Z"
        DESCRIPTION
            "Add  hwXQoSCarBindwidthExceedChipLimitAlarm,hwXQoSCarBindwidthExceedChipLimitResume"

     --add by tanyashi
        REVISION "202201132019Z"
        DESCRIPTION
            "Add  hwXQoSModeFlexeOverPortShapAlarmObjects, hwXQoSModeFlexeOverPortShapAlarm, hwXQoSModeFlexeOverPortShapAlarmClear"

     --add by huangliang
        REVISION "202112030955Z"
        DESCRIPTION
            "Modify hwXQoSPacketsDropInterfaceAlarm"

        REVISION "202111171446Z"
        DESCRIPTION
            "Delete useless comments"

     --add by qixin
        REVISION "202111012200Z"
        DESCRIPTION
            "Modify  hwXQoSUnsupportedActionAlarmObjects"

     --add by qixin
        REVISION "202110272200Z"
        DESCRIPTION
            "Add  hwXQoSUnsupportedActionAlarmObjects,hwXQoSUnsupportedActionAlarm,hwXQoSUnsupportedActionRusume"

     --add by qiaojuyang
        REVISION "202107271033Z"
        DESCRIPTION
            "ADD  hwXQoSModuleAlarmPatchStub, hwXQoSModuleAlarmPatchStubResume"

     --add by qiaojuyang
        REVISION "202107271033Z"
        DESCRIPTION
            "ADD  hwXQoSSlotAlarmPatchStub, hwXQoSSlotAlarmPatchStubResume"

     --add by qiaojuyang
        REVISION "202107271033Z"
        DESCRIPTION
            "ADD  hwXQoSDevAlarmPatchStub, hwXQoSDevAlarmPatchStubResume"

     --add by qixin
        REVISION "202107052230Z"
        DESCRIPTION
            "Add  hwXQoSUserQueueApplyPirExhaustionAlarmObjects,hwXQoSUserQueueApplyPirPreAlarmObjects,hwXQoSUserQueuePirAdjustAlarmObjects,hwXQoSUserQueueApplyPirExhaustionAlarm,hwXQoSUserQueueApplyPirPreAlarm,hwXQoSUserQueuePirAdjustAlarm"

     --add by zhoujing
        REVISION "202106221444Z"
        DESCRIPTION
            "Modify hwXQoSCarIfApplyDirection"

     --add by xushijie
        REVISION "202106101925Z"
        DESCRIPTION
            "Modify hwXQoSBaName"

     --add by chenlong
        REVISION "202106011501Z"
        DESCRIPTION
            "Modify hwXQoSPacketsDropInterfaceAlarmResume and hwXQoSPacketsDropInterfaceAlarmTable"

     --add by wangjian
        REVISION "202105271621Z"
        DESCRIPTION
            "Modify  hwXQoSOutPfcTurnOff, hwXQoSOutPfcTurnOffResume"

     --add by wangjian
        REVISION "202105261534Z"
        DESCRIPTION
            "ADD  hwXQoSOutPfcTurnOff, hwXQoSOutPfcTurnOffResume"

     --add by qixin
        REVISION "202104211150Z"
        DESCRIPTION
            "Delete  hwXQoSBgpFlowspecDestinationOriginAsOverAlarmObjects"

     --add by qixin
        REVISION "202104091150Z"
        DESCRIPTION
            "ADD  hwXQoSInterfaceDownRedirectNextHopInvalidAlarmObjects,hwXQoSInterfaceDownRedirectNextHopInvalidAlarm,hwXQoSInterfaceDownRedirectNextHopInvalidAlarmClear,hwXQoSRedirectNextHopEventLogObjects, hwXQoSRedirectNextHopEventLog, hwXQoSBgpFlowspecDestinationOriginAsOverAlarm, hwXQoSBgpFlowspecDestinationOriginAsOverAlarmClear, hwXQoSBgpFlowspecDestinationOriginAsOverAlarmObjects"

     --add by dongyanan
        REVISION "202103041030Z"
        DESCRIPTION
            "ADD  hwXQoSModeChannelOverBandwidthAlarm, hwXQoSModeChannelOverBandwidthAlarmResume"

     --add by dongyanan
        REVISION "202101122046Z"
        DESCRIPTION
            "ADD  hwXQoSModeChannelOverBandwidthAlarm, hwXQoSModeChannelOverBandwidthAlarmResume, hwXQoSUserQueueResPoolIndex"

     --add by wuyifan wx191562
        REVISION "202101061003Z"
        DESCRIPTION
            "Modify  hwXQoSUserQueueResPoolIndex,hwXQoSUserGroupQueueResPoolIndex,hwXQoSSubPortQueueResPoolIndex"

        REVISION "202010260926Z"
        DESCRIPTION
            "ADD hwXQoSBDStormSuppressAlarm, hwXQoSBDStormSuppressAlarmResume"

        REVISION "202010091929Z"
        DESCRIPTION
            "ADD hwXQoSVlanStormSuppressAlarm, hwXQoSVlanStormSuppressAlarmResume"

        REVISION "202010091231Z"
        DESCRIPTION
            "Modify type of hwXQoSBUMReplicationAlarmChipId"

        REVISION "202009151845Z"
        DESCRIPTION
            "Modify name of hwXQoSPfcDeadLockAlarm"

        REVISION "202009141231Z"
        DESCRIPTION
            "Add name of hwXQoSBUMReplicationAlarm"

        REVISION "202009021131Z"
        DESCRIPTION
            "Modify name of hwXQoSUnsupportedFeatureAlarmResume"

        REVISION "202009011031Z"
        DESCRIPTION
            "ADD hwXQoSUnsupportedFeatureAlarmTable and hwXQoSUnsupportedFeatureAlarm and hwXQoSUnsupportedFeatureAlarmResume"

        REVISION "202007312000Z"
        DESCRIPTION
            "Modify name of hwXQOSResourceOverspecAlarm, hwXQOSResourceOverrunAlarm, hwXQOSResourceOverrunAlarmObjects, hwXQOSResourceOverrunAlarmTable, hwXQOSResourceOverrunAlarmEntry, hwXQOSResourceOverspecAlarmObjects, hwXQOSResourceOverspecAlarmTable, hwXQOSResourceOverspecAlarmEntry"

        REVISION "202007281031Z"
        DESCRIPTION
            "ADD hwXQoSRedirectNextHopLackResAlarmTable and hwXQoSRedirectNextHopLackResAlarm and hwXQoSRedirectNextHopLackResAlarmClear"

        REVISION "202007241724Z"
        DESCRIPTION
            "Modify access of hwXQoSPfcDeadLockAlarm"

        REVISION "202007241019Z"
        DESCRIPTION
            "Modify description of hwXQoSStormSuppressAlarm hwXQoSStormSuppressAlarmResume hwXQoSStormControlAction hwXQoSStormControlStatus hwXQoSStormControlUnknownUnicastMinRate"

        REVISION "202007211711Z"
        DESCRIPTION
            "Add DESCRIPTIONof hwXQOSResourceOverspecAlarm, hwXQOSResourceOverspecAlarmResume, hwXQOSResourceOverrunAlarm, hwXQOSResourceOverrunAlarmResume"

        REVISION "202007202150Z"
        DESCRIPTION
            "Modify DESCRIPTIONof hwXQoSPfcApplyFailAlarm and hwXQoSPfcApplyFailAlarmResume"

        REVISION "202007201523Z"
        DESCRIPTION
            "Modify description of hwXQoSIfLrDiscardAlarm, hwXQoSRcyPortPktsDropAlarm, hwXQoSRcyPortPktsDropAlarmChipId, hwXQoSQueueStatisticsMulticastDropPkts, hwXQoSQueueStatisticsMulticastDropBytes, hwXQoSQueueStatisticsMulticastDropPktsRate, hwXQoSQueueStatisticsMulticastDropBytesRate, hwXQoSPacketsDropInterfaceAlarmSlotId, hwXQoSRcyPortPktsDropAlarmPortId, hwXQoSBufferOverrunHistoryTime, hwXQoSPacketsDropInterfaceAlarm, hwXQoSRcyPortPktsDropAlarmSlotId, hwXQoSPacketsDropInterfaceAlarmResume, hwXQoSBaRowStatus, hwXQoSBaName, hwXQoSBaIndex, hwXQoSBaPhbCfgInfoEntry, hwXQoSIfTrustEntry, hwXQoSRcyPortPktsDropAlarmResume, hwXQoSIfLrDiscardAlarmResume, hwXQoSIfQueueCosType, hwXQoSCarCbs, hwXQoSCarCir, hwXQoSCarPbs, hwXQoSCarPir, hwXQoSIfDiffDomainName, hwXQoSIfQueuePassededBytes, hwXQoSIfQueueTotalPackets, hwXQoSIfQueueDiscardedPacketRate and hwXQoSIfPhbEnableRowStatus"

        REVISION "202007161105Z"
        DESCRIPTION
            "Modify access of hwXQoSPfcApplyFailAlarm, hwXQoSPfcApplyFailAlarmResume, hwXQoSPfcTurnOff, hwXQoSPfcTurnOffResume, hwXQoSPfcDeadLock and hwXQoSPfcDeadLockResume "

        REVISION "202007081740Z"
        DESCRIPTION
            "Modify name of hwXACLResourceResume to hwXACLResourceAlarmResume"

        REVISION "202004291031Z"
        DESCRIPTION
            "Modify  OID of QoSModeChannelOverPortShapAlarm and  hwXQoSPfcInnerDeadLockAlarm"

        REVISION "202004271721Z"
        DESCRIPTION
            "Modify  description of hwXQoSCpDefendDiscardedByteRate and  hwXQoSCpDefendPassedByteRate"

        REVISION "202004261610Z"
        DESCRIPTION
            "Modify  hwXQoSUserQueueResourceEntry"

     --add by guohongbo
        REVISION "202003200850Z"
        DESCRIPTION
            "Modify  hwXQoSModeChannelOverPortShapAlarm describtion"

     --add by guohongbo
        REVISION "202003190850Z"
        DESCRIPTION
            "Modify  hwXQoSModeChannelOverPortShapAlarm describtion"

     --add by guohongbo
        REVISION "202003171915Z"
        DESCRIPTION
            "Modify  hwXQoSPortShapingBandwidthOverAlarm to hwXQoSModeChannelOverPortShapAlarm"

     --add by guohongbo
        REVISION "202003031151Z"
        DESCRIPTION
            "ADD  hwXQoSPortShapingBandwidthOverAlarm, hwXQoSPortShapingBandwidthOverAlarmClear"

        REVISION "201912301659Z"
        DESCRIPTION
            "MOD hwXACLResourceAlarm hwXACLResourceResume"

        REVISION "201910100953Z"
        DESCRIPTION
            "ADD hwXQoSPfcInnerDeadLockAlarm, hwXQoSPfcInnerDeadLockResume"

        REVISION "201909221054Z"
        DESCRIPTION
            "MOD hwXQOSQueueBufferOverrunAlarm hwXQOSQueueBufferOverrunResume "

        REVISION "201909221053Z"
        DESCRIPTION
            "MOD hwXQoSAclTcamResAclType"

     --add by xiaozhiguang
        REVISION "201909212026Z"
        DESCRIPTION
            "ADD hwXQoSTrafficSuppressionTrap, hwXQoSTrafficSuppIfIndex, hwXQoSTrafficSuppIfName, hwXQoSTrafficSuppBroadDropPkts, hwXQoSTrafficSuppMultiDropPkts, hwXQoSTrafficSuppUniDropPkts, hwXQoSTrafficSuppKnownMultiDropPkts, hwXQoSTrafficSuppKnownUniDropPkts, hwXQoSTrafficSuppressionEntry and hwXQoSTrafficSuppressionTable."

     --add by zhengjinke wx787338
        REVISION "201909190953Z"
        DESCRIPTION
            "MOD hwXQoSIfLrCfgVlanID"

     --add by dingsong
        REVISION "201906120953Z"
        DESCRIPTION
            "ADD hwXACLEPGGroupMemberV6Alarm, hwXACLEPGGroupMemberV6Resume"

     --add by panchao
        REVISION "201905141049Z"
        DESCRIPTION
            "MOD hwXQoSRedirectNextHopInvalidAlarmTable"

     --add by liuxu
        REVISION "201904221547Z"
        DESCRIPTION
            "MOD hwXQosCarResourceTable"

     --add by shenlin
        REVISION "201902282136Z"
        DESCRIPTION
            "MOD hwEnpPerformanceAlarm, hwEnpPerformanceAlarmResume"

     --add by liuxu
        REVISION "201902122126Z"
        DESCRIPTION
            "MOD ResetFlag, hwXQoSUserQueueResSlotID, hwXQoSUserGroupQueueResSlotID, hwXQoSSubPortQueueResSlotID, hwXQoSChannelResSlotID"

     --add by liuxu
        REVISION "201901300900Z"
        DESCRIPTION
            "MOD hwXQoSCpCarSlotId, hwXQoSBindingTrafficPolicyResSlotID, hwXQoSAclTcamResSlotID, hwXQoSBindingTrafficPolicyChassisResSlotID, hwXQoSCpDefendSlotId"

     --add by jiangruochen
        REVISION "201901221500Z"
        DESCRIPTION
            "ADD hwXQoSBindingTrafficPolicyChassisResourceTable"

     --add by xuehui
        REVISION "201812211406Z"
        DESCRIPTION
            "MOD hwXACLResourceAlarm, hwXACLResourceResume"

     --add by pengsheng
        REVISION "201812060940Z"
        DESCRIPTION
            "MOD hwXQoSPfcApplyFailAlarmResume, hwXQoSPfcTurnOffResume"

     --add by lihongling
        REVISION "201811231435Z"
        DESCRIPTION
            "add hwXQoSFlowWredResourceTable"

     --add by xuehui
        REVISION "201811202029Z"
        DESCRIPTION
            "MOD  hwXACLResourceAlarm , hwXACLResourceResume"

     --add by xuehui
        REVISION "201811141146Z"
        DESCRIPTION
            "MOD  hwXACLResourceAlarm , hwXACLResourceResume"

     --add by xuehui
        REVISION "201811061827Z"
        DESCRIPTION
            "ADD  hwXACLResourceAlarm , hwXACLResourceResume"

     --add by shenjiulong
        REVISION "201811052005Z"
        DESCRIPTION
            "ADD  hwXQOSFlowControlAlarm , hwXQOSFlowControlAlarmResume"

     --add by zhaoqingqing
        REVISION "201810271739Z"
        DESCRIPTION
            "ADD  hwXACLEPGEnableAlarm, hwXACLEPGEnableResume"

     --add by xuehui
        REVISION "201810220941Z"
        DESCRIPTION
            "MOD hwXACLEPGGroupMemberAlarmEntry"

     --add by dongyanhong
        REVISION "201809301739Z"
        DESCRIPTION
            "MOD hwXQoSStormControlAction, hwXQoSStormControlBcMode, hwXQoSStormControlMcMode, hwXQoSStormControlUcMode"

     --add by pengsheng
        REVISION "201809251739Z"
        DESCRIPTION
            "ADD  hwXQoSPfcApplyFailAlarm, hwXQoSPfcApplyFailAlarmResume"

     --add by zhaoqingqing
        REVISION "201809151739Z"
      DESCRIPTION
         "ADD  hwXACLEPGCreateGroupAlarm, hwXACLEPGCreateGroupResume, hwXACLEPGGroupMemberAlarm, hwXACLEPGGroupMemberResume, hwXACLEPGPolicyAlarm, hwXACLEPGPolicyResume"

     --add by zhaomingzhe
        REVISION "201809081730Z"
        DESCRIPTION
            "ADD  hwXQoSStormControlBroadcastRate, hwXQoSStormControlMulticastRate, hwXQoSStormControlUnicastRate"

     --add by yanghaopeng 84106631
        REVISION "201809031428Z"
        DESCRIPTION
            "MOD  hwXQoSHardPipeStatisticsExtTable, hwXQoSHardPipeAccessStatisticsExtTable, hwXQoSPortQueueStatisticsExtTable, hwXQoSIfQueueExtRunInfoTable"

     --add by yanghaopeng 84106631
        REVISION "201808221151Z"
        DESCRIPTION
            "ADD  hwXQoSHardPipeStatisticsExtTable, hwXQoSHardPipeAccessStatisticsExtTable, hwXQoSPortQueueStatisticsExtTable, hwXQoSIfQueueExtRunInfoTable"

     --add by gaolikun
        REVISION "201807311739Z"
        DESCRIPTION
            "ADD  hwXQoSTMPerformanceAlarm, hwXQoSTMPerformanceAlarmClear"

     --add by zhouzaihua
        REVISION "201807301739Z"
        DESCRIPTION
            "ADD  hwXQoSInterfaceIngressDropAlarm, hwXQoSInterfaceIngressDropAlarmResume"

     --add by xiejiayou WX353812
        REVISION "201807251546Z"
        DESCRIPTION
            "MOD hwXQoSPortShapPercent"

     --add by guanqingyu
        REVISION "201807031459Z"
        DESCRIPTION
            "Add hwXQoSCarStatisticsExtTable And hwXQoSIfCarStatisticsExtTable"

     --add by qilongfei
        REVISION "201806011739Z"
        DESCRIPTION
            "Add hwXQoSQppbPolicyStatisticsExtTable And hwXQoSQppbGlobalStatisticsExtTable"

     --add by luhongyu wx431419
        REVISION "201806011739Z"
        DESCRIPTION
            "MOD hwXQosCarResourceServiceType "

     --add by lidapeng
        REVISION "201805101739Z"
        DESCRIPTION
            "ADD hwXQoSHardPipeApplySQFailAlarm, hwXQoSHardPipeApplySQFailAlarmClear"

     --add by liyuanze
        REVISION "201804261739Z"
        DESCRIPTION
            "ADD  hwXACLFEIMemoryFullAlarm, hwXACLFEIMemoryFullAlarmResume"

     --add by zhouzaihua
        REVISION "201804251739Z"
        DESCRIPTION
            "ADD  hwXQoSQueueStatisticsMulticastObjects"

     --add by zhouzaihua
        REVISION "201804191739Z"
        DESCRIPTION
            "ADD  hwXQoSIfCarDiscardAlarm, hwXQoSIfCarDiscardAlarmResume"

     --add by wangyan
        REVISION "201804161739Z"
        DESCRIPTION
            "ADD  hwXACLFEIMemoryFullAlarm, hwXACLFEIMemoryFullAlarmResume"

        REVISION "201804161739Z"
        DESCRIPTION
            "ADD  hwXQoSPfcTurnOff, hwXQoSPfcTurnOffResume"

        REVISION "201803161550Z"
        DESCRIPTION
            "MOD  hwXQoSAclTcamResTotalNumbe"

        REVISION "201801311139Z"
        DESCRIPTION
            "MOD  hwXQoSCpApplyPolicyName,hwXQoSCpCarActionPolicyName, hwXQoSCBPairResTrafficPolicyName"

     --add by hanhongyun
        REVISION "201801231739Z"
        DESCRIPTION
            "ADD  hwXQoSPfcDeadLock, hwXQoSPfcDeadLockResume"

     --add by hehaiyan
        REVISION "201801221739Z"
        DESCRIPTION
            "ADD  hwXQosQueueExcepAlarm, hwXQosQueueExcepAlarmResume"

     --add by hehaiyan
        REVISION "201801151739Z"
        DESCRIPTION
            "MOD  hwXQoSPortQueueStatisticsQueueIndex, "

        REVISION "201801021739Z"
        DESCRIPTION
            "MOD  hwXQoSPortQueueStatisticsQueueIndex, "

     --add by wuyifan wx191562
        REVISION "201712211530Z"
        DESCRIPTION
            "SNMPv2-TC.hwQoS OBJECT IDENTIFIER.hwXQoSIfWredCfgInfoEntry"

        REVISION "201712070948Z"
        DESCRIPTION
            "The HUAWEI-XQoS-MIB contains objects to
            Manage configuration and Monitor running state
            for Class Based QoS feature."

     --add by tianhao
        REVISION "201711101739Z"
        DESCRIPTION
            "MOD  HwXQoSIfQueueRunInfoEntry, "

     --add by zhouzaihua
        REVISION "201710231739Z"
        DESCRIPTION
            "ADD  hwXQoSIngressAgingDiscardAlarm, hwXQoSIngressAgingDiscardAlarmResume"

         --add by chenxu wx398575
        REVISION "201710171739Z"
        DESCRIPTION
            "MOD  hwXQoSHardPipeAlarm, hwXQoSSoftPipeAlarm, hwXQoSHardPipeBwAlarm"

        REVISION "201709021739Z"
        DESCRIPTION
            "MODIFY  hwXQoSRedirectNextHopInvalidAlarm,hwXQoSRedirectNextHopInvalidAlarmClear"
     --add by yejun
        REVISION "201707290406Z"
        DESCRIPTION
            "MODIFY  hwXQoSHardPipeAlarmTable,hwXQoSSoftPipeAlarmTable,hwXQoSHardPipeBwAlarmTable"

     --add by zhouzaihua
        REVISION "201707251739Z"
        DESCRIPTION
            "ADD  hwXQosIngressPktsDiscardAlarm, hwXQoSIngressPktsDiscardAlarmResume"

     --add by sunqirui
        REVISION "201707041532Z"
        DESCRIPTION
            "ADD  hwXQoSStormSuppressAlarm, hwXQoSStormSuppressAlarmResume, hwXQoSStormSuppressSlotAlarm, hwXQoSStormSuppressSlotAlarmResume"

     --add by chenxu wx398575
        REVISION "201707011739Z"
        DESCRIPTION
            "ADD  hwXQoSHardPipeAcBandWthOverAlarm,hwXQoSHardPipeAcBandWthOverAlarmClear"

     --add by chenxu wx398575
        REVISION "201707011739Z"
        DESCRIPTION
            "MODIFY  hwXQoSHardPipeStatisticsTable"

     --add by zhouzaihua
        REVISION "201707011739Z"
        DESCRIPTION
            "ADD  hwXQoUnicastPktsDiscardAlarm, hwXQoSUnicastPktsDiscardAlarmResume"

        REVISION "201707011739Z"
        DESCRIPTION
            "ADD  hwXQoSPortShapPercent"

     --add by guanjiazhi wx451239
        REVISION "201706161739Z"
        DESCRIPTION
            "ADD  hwXQoSIfCarCfgInfoTable, hwXQoSIfLrCfgInfoTable, hwXQoSIfQueueCfgInfoTable, hwXQoSIfQueueRunInfoTable, hwXQoSIfCarStatisticsTable, hwXQoSUserQueueResourceTable, hwXQoSUserGroupQueueResourceTable, hwXQoSSubPortQueueResourceTable, hwXQoSChannelResourceTable, hwXQoSTemplateResourceTable, hwXQoSCBPairResourceTable, hwXQoSBindingTrafficPolicyResourceTable, hwXQoSAclTcamResourceTable, hwXQosBoardCarResourceTable, hwXQoSPortQueueAlarmExTable "

     --add by zhouzaihua
        REVISION "201706131739Z"
        DESCRIPTION
            "ADD  hwXQoSRcyPortPktsDropAlarm, hwXQoSRcyPortPktsDropAlarmResume"

     --add by luhongyu wx431419
        REVISION "201705061438Z"
        DESCRIPTION
            "ADD hwXQoSIfLrRealCir"

     --add by zhouzaihua
        REVISION "201705041739Z"
        DESCRIPTION
            "ADD  hwXQoSPacketsDropInterfaceAlarm, hwXQoSPacketsDropInterfaceAlarmResume"

     --add by sunqirui
        REVISION "201702251739Z"
        DESCRIPTION
            "ADD  hwXQoSStormControlAlarm, hwXQoSStormControlAlarmResume"

     --add by chenxuegang wx283757
        REVISION "201702241736Z"
        DESCRIPTION
            "MOD  hwXQoSCarStatisticsSlotNumber"

     --add by zhouzaihua
        REVISION "201702241022Z"
        DESCRIPTION
            "ADD  hwXQoSUnicastPktsCongestionAlarm, hwXQoSUnicastPktsCongestionAlarmResume"

     --add by wanghongke wx228773
        REVISION "201701161022Z"
        DESCRIPTION
            "ADD hwXQoSSubPortQueueResPoolIndex TABLE"

     --add by liangyun
        REVISION "201701131548Z"
        DESCRIPTION
            "ADD hwXQoSHardPipeAccessStatisticsTable TABLE"

     --add by wangcheng
        REVISION "201612211251Z"
        DESCRIPTION
            "ADD hwXQoSCarObjects"

     --add by lizhen
        REVISION "201611291251Z"
        DESCRIPTION
            "ADD hwXQoSHardPipeBwAlarmTable NODE"

        REVISION "201611171628Z"
        DESCRIPTION
            "ADD add hwXQOSQueueBufferAlarmDiscard "

     --add by zhangmingming
        REVISION "201609291932Z"
        DESCRIPTION
            "Modify hwXQoSCpDefendDiscardedPacketAlarm"

        REVISION "201609211021Z"
        DESCRIPTION
            "ADD hwXQoSHardPipeApplyFailAlarm at 2016-09-21."

     --add by pengsheng
        REVISION "201609031739Z"
        DESCRIPTION
            "ADD  hwXQoSMulticastPktsDiscardAlarm, hwXQoSMulticastPktsDiscardAlarmResume, hwXQoSMulticastPktsDiscardInterfaceAlarm, hwXQoSMulticastPktsDiscardInterfaceAlarmResume"

        REVISION "201606201428Z"
        DESCRIPTION
            "ADD hwXQoSSoftPipeAlarmTable NODE "

     --add by dongyanan
        REVISION "201606011201Z"
        DESCRIPTION
            "modify hwXQoSIfQueueCfgInfoTable"

     --add by magang
        REVISION "201605311447Z"
        DESCRIPTION
            "add hwXQoSQppbPolicyEventLog, hwXQoSQppbPolicyEventLogObjects"

        REVISION "201604211021Z"
        DESCRIPTION
            "MODIFY hwXQoSIfQueueCfgCosType at 2016-8-8."

        REVISION "201604211021Z"
        DESCRIPTION
            "MODIFY hwXQoSPortShapingPbsValue"

    --add by magang
      REVISION "201604051930Z"
       DESCRIPTION
          "add hwXQoSGlbQPPBEventLog, hwXQoSGlbQPPBEventLogObjects"

     -- added by chenhao
        REVISION "201603221436Z"
        DESCRIPTION
            "add VB node of hwXQoSDefendPortCarPassedPacketAlarm and hwXQoSDefendPortCarPassedPacketAlarmClear"

        REVISION "201601191628Z"
        DESCRIPTION
            "ADD hwRemoteMirrRecoverFailNotify "

     --add by liye
        REVISION "201512142028Z"
        DESCRIPTION
            "ADD hwXQosBoardCarResourceTable"

     -- added by chenhao
        REVISION "201512041150Z"
        DESCRIPTION
            "add VB node of hwXQoSCpDefendDiscardedPacketAlarm and hwXQoSCpDefendDiscardedPacketAlarmClear"
        REVISION "201512021628Z"
        DESCRIPTION
            "ADD hwXQoSIf8021PCarCfgInfoTable "

        REVISION "201512021628Z"
        DESCRIPTION
            "modify hwXQoSBufferOverrunHistoryEntry"

     --add by magang
     REVISION "201511261851Z"
      DESCRIPTION
         "modify hwXQoSIfQPPBDelAlarm, hwXQoSIfQPPBDelAlarmObjects"

        REVISION "201511261128Z"
        DESCRIPTION
            "add hwXQoSBufferStatisticObjects"

     --add by magang
        REVISION "201510231050Z"
        DESCRIPTION
            "add hwXQoSIfQPPBDelAlarm, hwXQoSIfQPPBDelAlarmObjects"

     --add by songjian
        REVISION "201509161050Z"
        DESCRIPTION
            "add hwXQoSQppbPolicyApplyFailAlarm, hwXQoSQppbPolicyApplyFailAlarmClear, hwXQoSQppbPolicyApplyFailAlarmObjects"

     --add by wangzhensheng
        REVISION "201509081050Z"
        DESCRIPTION
            "add hwXQoSTrunkProfileNotEffectAlarm"

     --add by wangjing
        REVISION "201507161050Z"
        DESCRIPTION
            "renew description of  hwXQoSRuleFailAlarm, hwXQoSRuleFailInfo and hwXQoSRuleFailAlarmCancel"

     --add by wangjing
        REVISION "201506061428Z"
        DESCRIPTION
            "rename hwXQoSRuleFaileAlarm and hwXQoSRuleFaileAlarmCancel to hwXQoSRuleFailAlarm and hwXQoSRuleFailAlarmCancel"

        REVISION "201505201025Z"
        DESCRIPTION
            "CP-CAR Add hwXQoSCpDefendProtocolDescirption"

        REVISION "201504241025Z"
        DESCRIPTION
            "Modify hwXQoSStormControlTrap"

     -- added by chenhao
        REVISION "201501281030Z"
        DESCRIPTION
            "add trap node of hwXQoSDefendPortCarPassedPacketAlarm and hwXQoSDefendPortCarPassedPacketAlarmClear"

        REVISION "201412241428Z"
        DESCRIPTION
            "ADD hwXQoSChannelResourceTable"

        REVISION "201412231428Z"
        DESCRIPTION
            "ADD hwXQoSFCoEPriorityAlarm and hwXQoSFCoEPriorityAlarmClear"

     --add by wangjing
        REVISION "201412161428Z"
        DESCRIPTION
            "Modify hwXQoSVpnAclConflictAlarm, hwXQoSVpnAclConflictAlarmClear information "

     --add by wangjing
        REVISION "201412161428Z"
        DESCRIPTION
            "ADD hwXQoSVpnAclConflictAlarm, hwXQoSVpnAclConflictAlarmClear and hwXQoSVpnAclConflictAlarmTable"

        REVISION "201412151428Z"
        DESCRIPTION
            "ADD hwXQoSStormControlTrapExt and hwXQoSStormControlIfName"

        REVISION "201411031428Z"
        DESCRIPTION
            "ADD  hwXQoSIfLrDiscardAlarm, hwXQoSIfLrDiscardAlarmResume"

        REVISION "201410101428Z"
        DESCRIPTION
            "ADD hwXQoSHardPipeAbilityTable and hwXQoSHardPipeConfigTable"

        REVISION "201408151428Z"
        DESCRIPTION
            "DEL hwXQoSBaFrdePhbTable and hwXQoSBaFrdeMapTable and hwXQoSIfTrustFrdeTable"

        REVISION "201408071428Z"
        DESCRIPTION
            "MOD hwXQoSHardPipeAlarmTable NODE"

        REVISION "201407301428Z"
        DESCRIPTION
            "ADD  hwXQOSQueueBufferOverrunAlarm, hwXQOSQueueBufferOverrunResume and hwXQOSQueueBufferOverrunAlarmTable"

        REVISION "201407231428Z"
        DESCRIPTION
            "ADD  hwXQoSUserQueueResourceTable, hwXQoSUserGroupQueueResourceTable,
            hwXQoSSubPortQueueResourceTable,  hwXQoSChannelResourceTable,
            hwXQoSTemplateResourceTable,  hwXQoSCBPairResourceTable,
            hwXQoSBindingTrafficPolicyResourceTable,  and  hwXQoSAclTcamResourceTable"

        REVISION "201407101428Z"
        DESCRIPTION
            "ADD hwXQoSBaFrdePhbTable and hwXQoSBaFrdeMapTable and hwXQoSIfTrustFrdeTable"

        REVISION "201407091428Z"
        DESCRIPTION
            "ADD hwXQoSHardPipeStatisticsTable"

        REVISION "201407021428Z"
        DESCRIPTION
            "MOD hwXQoSRuleFaileAlarmCancel NODE"

        REVISION "201404241428Z"
        DESCRIPTION
            "MOD hwXQoSProfileName NODE"

        REVISION "201403311428Z"
        DESCRIPTION
            "MOD hwXQoSBufferUsageStatisticsObjects OID"

        REVISION "201401221428Z"
        DESCRIPTION
            "ADD hwXQoSPortQueueAlarmExTable"

        REVISION "201401181428Z"
        DESCRIPTION
            "MOD hwXQoSIfQueueRunInfoTable and hwXQoSPortQueueStatisticsTable"

        REVISION "201312161428Z"
        DESCRIPTION
            "MOD hwXQoSCarTable and hwXQoSIfCarCfgInfoTable"

        REVISION "201309291428Z"
        DESCRIPTION
            "MOD hwXQoSCarTable OID"

        REVISION "201307291428Z"
        DESCRIPTION
            "ADD hwXQosCarResourceTable"

        REVISION "201306031428Z"
        DESCRIPTION
            "MOD hwXQoSProfileObjects and hwXQoSPortQueueAlarmObjects OID"

        REVISION "201304271428Z"
        DESCRIPTION
            "ADD hwXQoSPortQueueStatisticsQueuePercentage NODE"

        ::= { hwQoS 4 }
--   1.3.6.1.4.1.2011.5.25.32.4
--
-- Textual conventions
--
--
-- type definitions in the interface queue
--
-- hwXQosQueueType
    XQosQueueType ::= TEXTUAL-CONVENTION
        STATUS current
        DESCRIPTION
            "Queue Type:
            BE (1)
            AF1(2)
            AF2(3)
            AF3(4)
            AF4(5)
            EF (6)
            "
        SYNTAX INTEGER
            {
            be(1),
            af1(2),
            af2(3),
            af3(4),
            af4(5),
            ef(6)
            }

-- ResetFlag
    ResetFlag ::= TEXTUAL-CONVENTION
        STATUS current
        DESCRIPTION
            "Reset Flag:
            DISABLE (0)
            RESET   (1)
            ENABLE  (2)
            "
        SYNTAX INTEGER
            {
            disable(0),
            reset(1),
            enable(2)
            }

--    COS Type
    CosType ::= TEXTUAL-CONVENTION
        STATUS current
        DESCRIPTION
            "
            BE(1)
            AF1(2)
            AF2(3)
            AF3(4)
            AF4(5)
            EF(6)
            CS6(7)
            CS7(8)
            ALL(9)
            queue10(10)
            queue11(11)
            queue12(12)
            queue13(13)
            queue14(14)
            queue15(15)
            queue16(16)
            queue17(17)
            queue18(18)
            queue19(19)
            queue20(20)
            queue21(21)
            queue22(22)
            queue23(23)
            queue24(24)
            "
        SYNTAX INTEGER
            {
            be(1),
            af1(2),
            af2(3),
            af3(4),
            af4(5),
            ef(6),
            cs6(7),
            cs7(8),
            all(9),
            queue10(10),
            queue11(11),
            queue12(12),
            queue13(13),
            queue14(14),
            queue15(15),
            queue16(16),
            queue17(17),
            queue18(18),
            queue19(19),
            queue20(20),
            queue21(21),
            queue22(22),
            queue23(23),
            queue24(24)
            }

--   CarAction
    CarAction ::= TEXTUAL-CONVENTION
        STATUS current
        DESCRIPTION
            "The actions taken when packets conforming or exceeding the configured
            CIR:
                pass (1),
                discard (2),
                remark IP Precedence (3),
                remark DSCP(4),
                remark Mpls Exp(5),
                remark (6),
                remark 8021p(7)
            "
        SYNTAX INTEGER
            {
            pass(1),
            discard(2),
            remarkIpPrec(3),
            remarkDscp(4),
            remarkMplsExp(5),
            remark(6),
            remark8021p(7)
            }

--   Direction
    DirectionType ::= TEXTUAL-CONVENTION
        STATUS current
        DESCRIPTION
            "The Direction Policy apply on."
        SYNTAX INTEGER
            {
            inbound(1),
            outbound(2)
            }

--   UrpfCtrlType
    UrpfCtrlType ::= TEXTUAL-CONVENTION
        STATUS current
        DESCRIPTION
            "Strict(1)
            Loose(2)"
        SYNTAX INTEGER
            {
            strict(1),
            loose(2)
            }

--   SampleType
    SampleType ::= TEXTUAL-CONVENTION
        STATUS current
        DESCRIPTION
            "Fix-packets(1)
            Fix-time(2)
            Random-packets(3)
            Random-time(4)
            "
        SYNTAX INTEGER
            {
            fix-packets(1),
            fix-time(2),
            random-packets(3),
            random-time(4)
            }

-- IPCARRuleType
        IPCARRuleType ::= TEXTUAL-CONVENTION
            STATUS current
            DESCRIPTION
                "Type of IPCAR Rule. "
            SYNTAX INTEGER
                {
                ipv4Acl(1),
                ipv4SrcIp(2),
                ipv4DstIp(3)
                }

--   PolicyDirectionType
    PolicyDirectionType ::= TEXTUAL-CONVENTION
        STATUS current
        DESCRIPTION
            "In-outbound(0)
            Inbound(1)
            Outbound(2)
            "
        SYNTAX INTEGER
            {
            In-outbound(0),
            Inbound(1),
            Outbound(2)
            }
--
--   FwdResourceOverloadType
    FwdResourceOverloadType ::= TEXTUAL-CONVENTION
        STATUS current
        DESCRIPTION
            "BandWidthExceed(1)
            "
        SYNTAX INTEGER
            {
            BandWidthExceed(1)
            }
--
-- Node definitions
--

-- 1.3.6.1.4.1.2011.5.25.32
--  hwQoS OBJECT IDENTIFIER ::= { hwDatacomm 32 }

--  1.3.6.1.4.1.2011.5.25.32.4.1
    hwXQoSObjects OBJECT IDENTIFIER ::= { hwXQoSMIB 1 }
    hwXQoSConformance OBJECT IDENTIFIER ::= { hwXQoSMIB 2 }

--   BA command
    hwXQoSBaObjects OBJECT IDENTIFIER ::= { hwXQoSObjects 1 }

--    Diffserv Domain
    hwXQoSBaCfgInfoTable OBJECT-TYPE
        SYNTAX SEQUENCE OF HwXQoSBaCfgInfoEntry
        MAX-ACCESS not-accessible
        STATUS current
        DESCRIPTION
            "A table of diff-server domain configuration information."
        ::= { hwXQoSBaObjects 1 }

    hwXQoSBaCfgInfoEntry OBJECT-TYPE
        SYNTAX HwXQoSBaCfgInfoEntry
        MAX-ACCESS not-accessible
        STATUS current
        DESCRIPTION
            "Diff-server domain Information Entry."
        INDEX { hwXQoSBaIndex }
        ::= { hwXQoSBaCfgInfoTable 1 }

    HwXQoSBaCfgInfoEntry ::=
        SEQUENCE {
            hwXQoSBaIndex
                Integer32,
            hwXQoSBaName
                OCTET STRING,
            hwXQoSBaRowStatus
                RowStatus
         }

    hwXQoSBaIndex OBJECT-TYPE
        SYNTAX Integer32
        MAX-ACCESS read-only
        STATUS current
        DESCRIPTION
            "The value of this object identifies the index of a DS domain. The value ranges from 0 to 7. This object has no default value."
        ::= { hwXQoSBaCfgInfoEntry 1 }

    hwXQoSBaName OBJECT-TYPE
        SYNTAX OCTET STRING (SIZE (1..31))
        MAX-ACCESS read-create
        STATUS current
        DESCRIPTION
            "This object indicates the name of a DS domain. The value of this object is a string of 1 to 8 ASCII characters in plain text and complies with the format of the command line. The object has no default value."
        ::= { hwXQoSBaCfgInfoEntry 2 }

    hwXQoSBaRowStatus OBJECT-TYPE
        SYNTAX RowStatus
        MAX-ACCESS read-create
        STATUS current
        DESCRIPTION
            "The value of this object identifies the row status. The value of this object can be any of the following: CreateAndGo(4), Destroy(6), Active(1). The object has no default value."
        ::= { hwXQoSBaCfgInfoEntry 3 }

--    8021p-inbound in diff domain
    hwXQoSBa8021pPhbCfgInfoTable OBJECT-TYPE
        SYNTAX SEQUENCE OF HwXQoSBa8021pPhbCfgInfoEntry
        MAX-ACCESS not-accessible
        STATUS current
        DESCRIPTION
            "A table of diff-serve domain 8021p phb configuration information."
        ::= { hwXQoSBaObjects 2 }

    hwXQoSBa8021pPhbCfgInfoEntry OBJECT-TYPE
        SYNTAX HwXQoSBa8021pPhbCfgInfoEntry
        MAX-ACCESS not-accessible
        STATUS current
        DESCRIPTION
            "Diff-serve domain 8021p phb Configuration Information Entry."
        INDEX { hwXQoSBaIndex, hwXQoSBa8021pPhbIndex }
        ::= { hwXQoSBa8021pPhbCfgInfoTable 1 }

    HwXQoSBa8021pPhbCfgInfoEntry ::=
        SEQUENCE {
            hwXQoSBa8021pPhbIndex
                Integer32,
            hwXQoSBa8021pPhbPri
                Integer32,
            hwXQoSBa8021pPhbCos
                Integer32,
            hwXQoSBa8021pPhbColour
                Integer32,
            hwXQoSBa8021pPhbRowStatus
                RowStatus
         }

    hwXQoSBa8021pPhbIndex OBJECT-TYPE
        SYNTAX Integer32
        MAX-ACCESS read-only
        STATUS current
        DESCRIPTION
            "The value of this object identifies the index of the Per-Hop Behavior (PHB)."
        ::= { hwXQoSBa8021pPhbCfgInfoEntry 1 }

    hwXQoSBa8021pPhbPri OBJECT-TYPE
        SYNTAX Integer32
        MAX-ACCESS read-only
        STATUS current
        DESCRIPTION
            "The value of this object identifies the 802.1p priority.The value ranges from 0 to 7."
        ::= { hwXQoSBa8021pPhbCfgInfoEntry 2 }

    hwXQoSBa8021pPhbCos OBJECT-TYPE
        SYNTAX Integer32
        MAX-ACCESS read-write
        STATUS current
        DESCRIPTION
            "The value of this object identifies CoS, that is, the scheduling priority.The value can be any of the following:CS7(7),CS6(6),EF(5),AF4(4),AF3(3),AF2(2),AF1(1),BE(0)."
        ::= { hwXQoSBa8021pPhbCfgInfoEntry 3 }

    hwXQoSBa8021pPhbColour OBJECT-TYPE
        SYNTAX Integer32
        MAX-ACCESS read-write
        STATUS current
        DESCRIPTION
            "The value of this object identifies the color of the packet, that is, the discarding priority.The value can be any of the following:Green(0),Yellow(1),Red(2)."
        ::= { hwXQoSBa8021pPhbCfgInfoEntry 4 }

    hwXQoSBa8021pPhbRowStatus OBJECT-TYPE
        SYNTAX RowStatus
        MAX-ACCESS read-create
        STATUS current
        DESCRIPTION
            "The value of this object identifies the row status.The value can be any of the following:CreateAndGo(4),Destroy(6),Active(1)."
        ::= { hwXQoSBa8021pPhbCfgInfoEntry 5 }

--    8021p-outbound in diff domain
    hwXQoSBa8021pMapCfgInfoTable OBJECT-TYPE
        SYNTAX SEQUENCE OF HwXQoSBa8021pMapCfgInfoEntry
        MAX-ACCESS not-accessible
        STATUS current
        DESCRIPTION
            "A table of diff-serve domain 8021p map configuration information."
        ::= { hwXQoSBaObjects 3 }

    hwXQoSBa8021pMapCfgInfoEntry OBJECT-TYPE
        SYNTAX HwXQoSBa8021pMapCfgInfoEntry
        MAX-ACCESS not-accessible
        STATUS current
        DESCRIPTION
            "Diff-serve domain 8021p map Configuration Information Entry."
        INDEX { hwXQoSBaIndex, hwXQoSBa8021pMapIndex }
        ::= { hwXQoSBa8021pMapCfgInfoTable 1 }

    HwXQoSBa8021pMapCfgInfoEntry ::=
        SEQUENCE {
            hwXQoSBa8021pMapIndex
                Integer32,
            hwXQoSBa8021pMapCos
                Integer32,
            hwXQoSBa8021pMapColour
                Integer32,
            hwXQoSBa8021pMapPri
                Integer32,
            hwXQoSBa8021pMapRowStatus
                RowStatus
         }

    hwXQoSBa8021pMapIndex OBJECT-TYPE
        SYNTAX Integer32
        MAX-ACCESS read-only
        STATUS current
        DESCRIPTION
            "The value of this object identifies the mapping index.The value starts from 0."
        ::= { hwXQoSBa8021pMapCfgInfoEntry 1 }

    hwXQoSBa8021pMapCos OBJECT-TYPE
        SYNTAX Integer32
        MAX-ACCESS read-only
        STATUS current
        DESCRIPTION
            "The value of this object identifies CoS, that is, the scheduling priority.The value can be any of the following:
CS7(7),CS6(6),EF(5),AF4(4),AF3(3),AF2(2),AF1(1),BE(0)."
        ::= { hwXQoSBa8021pMapCfgInfoEntry 2 }

    hwXQoSBa8021pMapColour OBJECT-TYPE
        SYNTAX Integer32
         MAX-ACCESS read-only
        STATUS current
        DESCRIPTION
            "The value of this object identifies the color of the packet, that is, the discarding priority.The value can be any of the following:Green(0),Yellow(1),Red(2)."
        ::= { hwXQoSBa8021pMapCfgInfoEntry 3 }

    hwXQoSBa8021pMapPri OBJECT-TYPE
        SYNTAX Integer32
        MAX-ACCESS read-write
        STATUS current
        DESCRIPTION
            "The value of this object identifies the 8021.p priority.The value ranges from 0 to 7.The object has no default value."
        ::= { hwXQoSBa8021pMapCfgInfoEntry 4 }

    hwXQoSBa8021pMapRowStatus OBJECT-TYPE
        SYNTAX RowStatus
        MAX-ACCESS read-create
        STATUS current
        DESCRIPTION
            "The value of this object identifies the row status.The value can be any of the following:CreateAndGo(4),Destroy(6),Active(1).The object has no default value."
        ::= { hwXQoSBa8021pMapCfgInfoEntry 5 }

--    Dscp-inbound in diff domain
    hwXQoSBaDscpPhbCfgInfoTable OBJECT-TYPE
        SYNTAX SEQUENCE OF HwXQoSBaDscpPhbCfgInfoEntry
        MAX-ACCESS not-accessible
        STATUS current
        DESCRIPTION
            "A table of diff-serve domain DSCP phb configuration information."
        ::= { hwXQoSBaObjects 4 }

    hwXQoSBaDscpPhbCfgInfoEntry OBJECT-TYPE
        SYNTAX HwXQoSBaDscpPhbCfgInfoEntry
        MAX-ACCESS not-accessible
        STATUS current
        DESCRIPTION
            "Diff-serve domain DSCP phb Configuration Information Entry."
        INDEX { hwXQoSBaIndex, hwXQoSBaDscpPhbIndex }
        ::= { hwXQoSBaDscpPhbCfgInfoTable 1 }

    HwXQoSBaDscpPhbCfgInfoEntry ::=
        SEQUENCE {
            hwXQoSBaDscpPhbIndex
                Integer32,
            hwXQoSBaDscpPhbPri
                Integer32,
            hwXQoSBaDscpPhbCos
                Integer32,
            hwXQoSBaDscpPhbColour
                Integer32,
            hwXQoSBaDscpPhbRowStatus
                RowStatus
         }

    hwXQoSBaDscpPhbIndex OBJECT-TYPE
        SYNTAX Integer32
        MAX-ACCESS read-only
        STATUS current
        DESCRIPTION
             "The value of this object identifies the index of the Per-Hop Behavior (PHB)."
        ::= { hwXQoSBaDscpPhbCfgInfoEntry 1 }

    hwXQoSBaDscpPhbPri OBJECT-TYPE
        SYNTAX Integer32
        MAX-ACCESS read-only
        STATUS current
        DESCRIPTION
            "The value of this object identifies the priority of DSCP.The value ranges from 0 to 7."
        ::= { hwXQoSBaDscpPhbCfgInfoEntry 2 }

    hwXQoSBaDscpPhbCos OBJECT-TYPE
        SYNTAX Integer32
        MAX-ACCESS read-write
        STATUS current
        DESCRIPTION
            "The value of this object identifies CoS, that is, the scheduling priority.The value can be any of the following:
CS(7),CS(6),EF(5),AF(4),AF(3),AF(2),AF(1),BE(0)."
        ::= { hwXQoSBaDscpPhbCfgInfoEntry 3 }

    hwXQoSBaDscpPhbColour OBJECT-TYPE
        SYNTAX Integer32
        MAX-ACCESS read-write
        STATUS current
        DESCRIPTION
            "The value of this object identifies the color of the packet, that is, the discarding priority.The value can be any of the following:Green(0),Yellow(1),Red(2)."
        ::= { hwXQoSBaDscpPhbCfgInfoEntry 4 }

    hwXQoSBaDscpPhbRowStatus OBJECT-TYPE
        SYNTAX RowStatus
        MAX-ACCESS read-create
        STATUS current
        DESCRIPTION
            "The value of this object identifies the row status.The value can be any of the following:CreateAndGo(4),Destroy(6),Active(1)."
        ::= { hwXQoSBaDscpPhbCfgInfoEntry 5 }

--    Dscp-outbound in diff domain
    hwXQoSBaDscpMapCfgInfoTable OBJECT-TYPE
        SYNTAX SEQUENCE OF HwXQoSBaDscpMapCfgInfoEntry
        MAX-ACCESS not-accessible
        STATUS current
        DESCRIPTION
            "A table of diff-serve domain Dscp map configuration information."
        ::= { hwXQoSBaObjects 5 }

    hwXQoSBaDscpMapCfgInfoEntry OBJECT-TYPE
        SYNTAX HwXQoSBaDscpMapCfgInfoEntry
        MAX-ACCESS not-accessible
        STATUS current
        DESCRIPTION
            "Diff-serve domain Dscp map Configuration Information Entry."
        INDEX { hwXQoSBaIndex, hwXQoSBaDscpMapIndex }
        ::= { hwXQoSBaDscpMapCfgInfoTable 1 }

    HwXQoSBaDscpMapCfgInfoEntry ::=
        SEQUENCE {
            hwXQoSBaDscpMapIndex
                Integer32,
            hwXQoSBaDscpMapCos
                Integer32,
            hwXQoSBaDscpMapColour
                Integer32,
            hwXQoSBaDscpMapPri
                Integer32,
            hwXQoSBaDscpMapRowStatus
                RowStatus
         }

    hwXQoSBaDscpMapIndex OBJECT-TYPE
        SYNTAX Integer32
        MAX-ACCESS read-only
        STATUS current
        DESCRIPTION
            "The value of this object identifies the mapping index."
        ::= { hwXQoSBaDscpMapCfgInfoEntry 1 }

    hwXQoSBaDscpMapCos OBJECT-TYPE
        SYNTAX Integer32
        MAX-ACCESS read-only
        STATUS current
        DESCRIPTION
            "The value of this object identifies CoS, that is, the scheduling priority.The value can be any of the following:
CS7(7),CS6(6),EF(5),AF4(4),AF3(3),AF2(2),AF1(1),BE(0)."
        ::= { hwXQoSBaDscpMapCfgInfoEntry 2 }

    hwXQoSBaDscpMapColour OBJECT-TYPE
        SYNTAX Integer32
        MAX-ACCESS read-only
        STATUS current
        DESCRIPTION
            "The value of this object identifies the color of the packet, that is, the discarding priority.The value can be any of the following:Green(0),Yellow(1),Red(2)."
        ::= { hwXQoSBaDscpMapCfgInfoEntry 3 }

    hwXQoSBaDscpMapPri OBJECT-TYPE
        SYNTAX Integer32
        MAX-ACCESS read-write
        STATUS current
        DESCRIPTION
            "The value of this object identifies the DSCP value.The value ranges from 0 to 7."
        ::= { hwXQoSBaDscpMapCfgInfoEntry 4 }

    hwXQoSBaDscpMapRowStatus OBJECT-TYPE
        SYNTAX RowStatus
        MAX-ACCESS read-create
        STATUS current
        DESCRIPTION
            "The value of this object identifies the row status.The value can be any of the following:CreateAndGo(4),Destroy(6),Active(1)."
        ::= { hwXQoSBaDscpMapCfgInfoEntry 5 }

--    Exp-inbound in diff domain
    hwXQoSBaExpPhbCfgInfoTable OBJECT-TYPE
        SYNTAX SEQUENCE OF HwXQoSBaExpPhbCfgInfoEntry
        MAX-ACCESS not-accessible
        STATUS current
        DESCRIPTION
            "A table of diff-serve domain Exp phb configuration information."
        ::= { hwXQoSBaObjects 6 }

    hwXQoSBaExpPhbCfgInfoEntry OBJECT-TYPE
        SYNTAX HwXQoSBaExpPhbCfgInfoEntry
        MAX-ACCESS not-accessible
        STATUS current
        DESCRIPTION
            "Diff-serve domain Exp phb Configuration Information Entry."
        INDEX { hwXQoSBaIndex, hwXQoSBaExpPhbIndex }
        ::= { hwXQoSBaExpPhbCfgInfoTable 1 }

    HwXQoSBaExpPhbCfgInfoEntry ::=
        SEQUENCE {
            hwXQoSBaExpPhbIndex
                Integer32,
            hwXQoSBaExpPhbPri
                Integer32,
            hwXQoSBaExpPhbCos
                Integer32,
            hwXQoSBaExpPhbColour
                Integer32,
            hwXQoSBaExpPhbRowStatus
                RowStatus
         }

    hwXQoSBaExpPhbIndex OBJECT-TYPE
        SYNTAX Integer32
        MAX-ACCESS read-only
        STATUS current
        DESCRIPTION
            "The value of this object identifies the index of PHB."
        ::= { hwXQoSBaExpPhbCfgInfoEntry 1 }

    hwXQoSBaExpPhbPri OBJECT-TYPE
        SYNTAX Integer32
        MAX-ACCESS read-only
        STATUS current
        DESCRIPTION
            "The value of this object identifies the EXP field of an MPLS packet.The value ranges from 0 to 7."
        ::= { hwXQoSBaExpPhbCfgInfoEntry 2 }

    hwXQoSBaExpPhbCos OBJECT-TYPE
        SYNTAX Integer32
        MAX-ACCESS read-write
        STATUS current
        DESCRIPTION
            "The value of this object identifies CoS, that is, the scheduling priority.The value can be any of the following:
CS7(7),CS6(6),EF(5),AF4(4),AF3(3),AF2(2),AF1(1),BE(0)."
        ::= { hwXQoSBaExpPhbCfgInfoEntry 3 }

    hwXQoSBaExpPhbColour OBJECT-TYPE
        SYNTAX Integer32
        MAX-ACCESS read-write
        STATUS current
        DESCRIPTION
             "The value of this object identifies the color of the packet, that is, the discarding priority.The value can be any of the following:Green(0),Yellow(1),Red(2)."
        ::= { hwXQoSBaExpPhbCfgInfoEntry 4 }

    hwXQoSBaExpPhbRowStatus OBJECT-TYPE
        SYNTAX RowStatus
        MAX-ACCESS read-create
        STATUS current
        DESCRIPTION
            "The value of this object identifies the row status.The value can be any of the following:CreateAndGo(4),Destroy(6),Active(1)."
        ::= { hwXQoSBaExpPhbCfgInfoEntry 5 }

--    Exp-outbound in diff domain
    hwXQoSBaExpMapCfgInfoTable OBJECT-TYPE
        SYNTAX SEQUENCE OF HwXQoSBaExpMapCfgInfoEntry
        MAX-ACCESS not-accessible
        STATUS current
        DESCRIPTION
            "A table of diff-serve domain Exp map configuration information."
        ::= { hwXQoSBaObjects 7 }

    hwXQoSBaExpMapCfgInfoEntry OBJECT-TYPE
        SYNTAX HwXQoSBaExpMapCfgInfoEntry
        MAX-ACCESS not-accessible
        STATUS current
        DESCRIPTION
            "Diff-serve domain Exp map Configuration Information Entry."
        INDEX { hwXQoSBaIndex, hwXQoSBaExpMapIndex }
        ::= { hwXQoSBaExpMapCfgInfoTable 1 }

    HwXQoSBaExpMapCfgInfoEntry ::=
        SEQUENCE {
            hwXQoSBaExpMapIndex
                Integer32,
            hwXQoSBaExpMapCos
                Integer32,
            hwXQoSBaExpMapColour
                Integer32,
            hwXQoSBaExpMapPri
                Integer32,
            hwXQoSBaExpMapRowStatus
                RowStatus
         }

    hwXQoSBaExpMapIndex OBJECT-TYPE
        SYNTAX Integer32
        MAX-ACCESS read-only
        STATUS current
        DESCRIPTION
            "The value of this object identifies the mapping index."
        ::= { hwXQoSBaExpMapCfgInfoEntry 1 }

    hwXQoSBaExpMapCos OBJECT-TYPE
        SYNTAX Integer32
        MAX-ACCESS read-only
        STATUS current
        DESCRIPTION
             "The value of this object identifies CoS, that is, the scheduling priority.The value can be any of the following:CS7(7),CS6(6),EF(5),AF4(4),AF3(3),AF2(2),AF1(1),BE(0)."
        ::= { hwXQoSBaExpMapCfgInfoEntry 2 }

    hwXQoSBaExpMapColour OBJECT-TYPE
        SYNTAX Integer32
        MAX-ACCESS read-only
        STATUS current
        DESCRIPTION
            "The value of this object identifies the color of the packet, that is, the discarding priority.The value can be any of the following:Green(0),Yellow(1),Red(2)."
        ::= { hwXQoSBaExpMapCfgInfoEntry 3 }

    hwXQoSBaExpMapPri OBJECT-TYPE
        SYNTAX Integer32
        MAX-ACCESS read-write
        STATUS current
        DESCRIPTION
            "The value of this object identifies the EXP field of the MPLS packet.The value ranges from 0 to 7."
        ::= { hwXQoSBaExpMapCfgInfoEntry 4 }

    hwXQoSBaExpMapRowStatus OBJECT-TYPE
        SYNTAX RowStatus
        MAX-ACCESS read-create
        STATUS current
        DESCRIPTION
            "The value of this object identifies the row status.The value can be any of the following:CreateAndGo(4),Destroy(6),Active(1)."
        ::= { hwXQoSBaExpMapCfgInfoEntry 5 }

--    trust upstream
    hwXQoSIfDiffDomainTable OBJECT-TYPE
        SYNTAX SEQUENCE OF HwXQoSIfDiffDomainEntry
        MAX-ACCESS not-accessible
        STATUS current
        DESCRIPTION
            "Trust upstream diff-serve domain, direction and VLAN are not supported.Only mode l2 sub-interfaces are supported."
        ::= { hwXQoSBaObjects 8 }

    hwXQoSIfDiffDomainEntry OBJECT-TYPE
        SYNTAX HwXQoSIfDiffDomainEntry
        MAX-ACCESS not-accessible
        STATUS current
        DESCRIPTION
            "Policy applied on interface Configuration Information Entry."
        INDEX { hwXQoSIfDiffDomainIfIndex, hwXQoSIfDiffDomainVlanId }
        ::= { hwXQoSIfDiffDomainTable 1 }

    HwXQoSIfDiffDomainEntry ::=
        SEQUENCE {
            hwXQoSIfDiffDomainIfIndex
                Integer32,
            hwXQoSIfDiffDomainVlanId
                Integer32,
            hwXQoSIfDiffDomainName
                OCTET STRING,
            hwXQoSIfDiffDomainRowStatus
                RowStatus,
            hwXQoSIfDiffDomainVlanId2
                Integer32
         }

    hwXQoSIfDiffDomainIfIndex OBJECT-TYPE
        SYNTAX Integer32
        MAX-ACCESS read-only
        STATUS current
        DESCRIPTION
            "The value of this object identifies the interface index."
        ::= { hwXQoSIfDiffDomainEntry 1 }

    hwXQoSIfDiffDomainVlanId OBJECT-TYPE
        SYNTAX Integer32 (0 | 1..4094)
        MAX-ACCESS read-only
        STATUS current
        DESCRIPTION
            "The value of this object identifies the VLAN ID of the interface. This object is not supported currently. The value of this object must be 0."
        ::= { hwXQoSIfDiffDomainEntry 2 }

    hwXQoSIfDiffDomainName OBJECT-TYPE
        SYNTAX OCTET STRING (SIZE (1..48))
        MAX-ACCESS read-create
        STATUS current
        DESCRIPTION
            "This object indicates the name of the DS domain. The name cannot contain Chinese characters."
        ::= { hwXQoSIfDiffDomainEntry 3 }

    hwXQoSIfDiffDomainRowStatus OBJECT-TYPE
        SYNTAX RowStatus
        MAX-ACCESS read-create
        STATUS current
        DESCRIPTION
            "This value of this object identifies the row status. The value can be any of the following: CreateAndGo(4), Destroy(6), Active(1)."
        ::= { hwXQoSIfDiffDomainEntry 4 }

    hwXQoSIfDiffDomainVlanId2 OBJECT-TYPE
        SYNTAX Integer32 (0 | 1..4094)
        MAX-ACCESS read-create
        STATUS current
        DESCRIPTION
            "End vlan ID. This object is not supported currently. The value of this object must be 0.
            -1 can't be set.
            0 is the default value"
        ::= { hwXQoSIfDiffDomainEntry 5 }

--    trust 8021p
    hwXQoSIfTrust8021pTable OBJECT-TYPE
        SYNTAX SEQUENCE OF HwXQoSIfTrust8021pEntry
        MAX-ACCESS not-accessible
        STATUS current
        DESCRIPTION
            "Trust diff-serve domain."
        ::= { hwXQoSBaObjects 9 }

    hwXQoSIfTrust8021pEntry OBJECT-TYPE
        SYNTAX HwXQoSIfTrust8021pEntry
        MAX-ACCESS not-accessible
        STATUS current
        DESCRIPTION
            "Policy applied on interface Configuration Information Entry."
        INDEX { hwXQoSIfTrust8021pIfIndex, hwXQoSIfTrust8021pVlanID }
        ::= { hwXQoSIfTrust8021pTable 1 }

    HwXQoSIfTrust8021pEntry ::=
        SEQUENCE {
            hwXQoSIfTrust8021pIfIndex
                Integer32,
            hwXQoSIfTrust8021pVlanID
                Integer32,
            hwXQoSIfTrust8021pAction
                INTEGER,
            hwXQoSIfTrust8021pRowStatus
                RowStatus
         }

    hwXQoSIfTrust8021pIfIndex OBJECT-TYPE
        SYNTAX Integer32
        MAX-ACCESS read-only
        STATUS current
        DESCRIPTION
            "The value of this object identifies the interface index."
        ::= { hwXQoSIfTrust8021pEntry 1 }

    hwXQoSIfTrust8021pVlanID OBJECT-TYPE
        SYNTAX Integer32 (0 | 1..4094)
        MAX-ACCESS read-only
        STATUS current
        DESCRIPTION
            "The value of this object identifies the VLAN ID of the interface."
        ::= { hwXQoSIfTrust8021pEntry 2 }

     hwXQoSIfTrust8021pAction OBJECT-TYPE
        SYNTAX INTEGER {
            distrust(1),
            trust(2)
           }
        MAX-ACCESS read-create
        STATUS current
        DESCRIPTION
            "The value of this object identifies whether the Layer 2 simple stream classification is enabled.The value can be either of the following:Distrust(1),Trust(2).The object has no default value."
        ::= { hwXQoSIfTrust8021pEntry 3 }

    hwXQoSIfTrust8021pRowStatus OBJECT-TYPE
        SYNTAX RowStatus
        MAX-ACCESS read-create
        STATUS current
        DESCRIPTION
            "This value of this object identifies the row status.The value can be any of the following:CreateAndGo(4),
Destroy(6),Active(1).The object has no default value."
        ::= { hwXQoSIfTrust8021pEntry 4 }

-- Atm Qos ServiceType+Clp to Cos+Color in diff domain
   hwXQoSBaAtmQosPhbCfgInfoTable OBJECT-TYPE
        SYNTAX SEQUENCE OF HwXQoSBaAtmQosPhbCfgInfoEntry
        MAX-ACCESS not-accessible
        STATUS current
        DESCRIPTION
            "A table of diff-serve domain AtmQos ServiceType+Clp phb configuration information."
        ::= { hwXQoSBaObjects 10 }

    hwXQoSBaAtmQosPhbCfgInfoEntry OBJECT-TYPE
        SYNTAX HwXQoSBaAtmQosPhbCfgInfoEntry
        MAX-ACCESS not-accessible
        STATUS current
        DESCRIPTION
            "Diff-serve domain AtmQos ServiceType+Clp phb Configuration Information Entry."
        INDEX { hwXQoSBaIndex, hwXQoSBaAtmQosPhbServType, hwXQoSBaAtmQosPhbClp  }
        ::= { hwXQoSBaAtmQosPhbCfgInfoTable 1 }

    HwXQoSBaAtmQosPhbCfgInfoEntry ::=
        SEQUENCE {
            hwXQoSBaAtmQosPhbServType
                Integer32,
            hwXQoSBaAtmQosPhbClp
                Integer32,
            hwXQoSBaAtmQosPhbCos
                Integer32,
            hwXQoSBaAtmQosPhbColour
                Integer32,
            hwXQoSBaAtmQosPhbRowStatus
                RowStatus
         }

    hwXQoSBaAtmQosPhbServType OBJECT-TYPE
        SYNTAX Integer32
        MAX-ACCESS read-only
        STATUS current
        DESCRIPTION
            "Atm Qos ServiceType."
        ::= { hwXQoSBaAtmQosPhbCfgInfoEntry 1 }

    hwXQoSBaAtmQosPhbClp OBJECT-TYPE
        SYNTAX Integer32
        MAX-ACCESS read-only
        STATUS current
        DESCRIPTION
            "Atm Qos Clp."
        ::= { hwXQoSBaAtmQosPhbCfgInfoEntry 2 }

    hwXQoSBaAtmQosPhbCos OBJECT-TYPE
        SYNTAX Integer32
        MAX-ACCESS read-write
        STATUS current
        DESCRIPTION
            "Cos of AtmQos."
        ::= { hwXQoSBaAtmQosPhbCfgInfoEntry 3 }

    hwXQoSBaAtmQosPhbColour OBJECT-TYPE
        SYNTAX Integer32
        MAX-ACCESS read-write
        STATUS current
        DESCRIPTION
            "Colour of AtmQos."
        ::= { hwXQoSBaAtmQosPhbCfgInfoEntry 4 }

    hwXQoSBaAtmQosPhbRowStatus OBJECT-TYPE
        SYNTAX RowStatus
        MAX-ACCESS read-create
        STATUS current
        DESCRIPTION
            "RowStatus. Three actions are used: active,
            createAndGo, destroy"
        ::= { hwXQoSBaAtmQosPhbCfgInfoEntry 5 }

--    Atm Qos Cos+Color to Clp in diff domain
    hwXQoSBaAtmQosMapCfgInfoTable OBJECT-TYPE
        SYNTAX SEQUENCE OF HwXQoSBaAtmQosMapCfgInfoEntry
        MAX-ACCESS not-accessible
        STATUS current
        DESCRIPTION
            "A table of diff-serve domain Atm Qos Clp map configuration information."
        ::= { hwXQoSBaObjects 11 }

    hwXQoSBaAtmQosMapCfgInfoEntry OBJECT-TYPE
        SYNTAX HwXQoSBaAtmQosMapCfgInfoEntry
        MAX-ACCESS not-accessible
        STATUS current
        DESCRIPTION
            "Diff-serve domain Atm Qos Clp map Configuration Information Entry."
        INDEX { hwXQoSBaIndex, hwXQoSBaAtmQosMapIndex}
        ::= { hwXQoSBaAtmQosMapCfgInfoTable 1 }

    HwXQoSBaAtmQosMapCfgInfoEntry ::=
        SEQUENCE {
            hwXQoSBaAtmQosMapIndex
                Integer32,
            hwXQoSBaAtmQosMapCos
                Integer32,
            hwXQoSBaAtmQosMapColour
                Integer32,
            hwXQoSBaAtmQosMapClp
                Integer32,
            hwXQoSBaAtmQosMapRowStatus
                RowStatus
         }

     hwXQoSBaAtmQosMapIndex OBJECT-TYPE
        SYNTAX Integer32
        MAX-ACCESS read-only
        STATUS current
        DESCRIPTION
            "Atm Qos index in diff-serve domain."
        ::= { hwXQoSBaAtmQosMapCfgInfoEntry 1 }

    hwXQoSBaAtmQosMapCos OBJECT-TYPE
        SYNTAX Integer32
        MAX-ACCESS read-only
        STATUS current
        DESCRIPTION
            "Cos of AtmQos."
        ::= { hwXQoSBaAtmQosMapCfgInfoEntry 2 }

    hwXQoSBaAtmQosMapColour OBJECT-TYPE
        SYNTAX Integer32
         MAX-ACCESS read-only
        STATUS current
        DESCRIPTION
            "Colour of AtmQos."
        ::= { hwXQoSBaAtmQosMapCfgInfoEntry 3 }

    hwXQoSBaAtmQosMapClp OBJECT-TYPE
        SYNTAX Integer32
        MAX-ACCESS read-write
        STATUS current
        DESCRIPTION
            "AtmQos Clp."
        ::= { hwXQoSBaAtmQosMapCfgInfoEntry 4 }

    hwXQoSBaAtmQosMapRowStatus OBJECT-TYPE
        SYNTAX RowStatus
        MAX-ACCESS read-create
        STATUS current
        DESCRIPTION
            "RowStatus. Three actions are used: active,
            createAndGo, destroy"
        ::= { hwXQoSBaAtmQosMapCfgInfoEntry 5 }

--    trust upstream on atm pvc
    hwXQoSAtmPvcDiffDomainTable OBJECT-TYPE
        SYNTAX SEQUENCE OF HwXQoSAtmPvcDiffDomainEntry
        MAX-ACCESS not-accessible
        STATUS current
        DESCRIPTION
            "Trust diff-serve domain."
        ::= { hwXQoSBaObjects 12 }

    hwXQoSAtmPvcDiffDomainEntry OBJECT-TYPE
        SYNTAX HwXQoSAtmPvcDiffDomainEntry
        MAX-ACCESS not-accessible
        STATUS current
        DESCRIPTION
            "Policy applied on pvc interface Configuration Information Entry."
        INDEX { hwXQoSAtmPvcDiffDomainIfIndex, hwXQoSAtmPvcVpi, hwXQoSAtmPvcVci}
        ::= { hwXQoSAtmPvcDiffDomainTable 1 }

    HwXQoSAtmPvcDiffDomainEntry ::=
        SEQUENCE {
            hwXQoSAtmPvcDiffDomainIfIndex
                Integer32,
            hwXQoSAtmPvcVpi
                Integer32,
            hwXQoSAtmPvcVci
                Integer32,
            hwXQoSAtmPvcDiffDomainName
                OCTET STRING,
            hwXQoSAtmPvcDiffDomainRowStatus
                RowStatus
         }

    hwXQoSAtmPvcDiffDomainIfIndex OBJECT-TYPE
        SYNTAX Integer32
        MAX-ACCESS read-only
        STATUS current
        DESCRIPTION
            "Atm Interface Index."
        ::= { hwXQoSAtmPvcDiffDomainEntry 1 }

    hwXQoSAtmPvcVpi OBJECT-TYPE
        SYNTAX Integer32
        MAX-ACCESS read-only
        STATUS current
        DESCRIPTION
            "Atm Pvc Vpi"
        ::= { hwXQoSAtmPvcDiffDomainEntry 2 }

    hwXQoSAtmPvcVci OBJECT-TYPE
        SYNTAX Integer32
        MAX-ACCESS read-only
        STATUS current
        DESCRIPTION
            "Atm Pvc Vci"
        ::= { hwXQoSAtmPvcDiffDomainEntry 3 }

    hwXQoSAtmPvcDiffDomainName OBJECT-TYPE
        SYNTAX OCTET STRING (SIZE (1..31))
        MAX-ACCESS read-create
        STATUS current
        DESCRIPTION
            "Name of diff-serve domain."
        ::= { hwXQoSAtmPvcDiffDomainEntry 4 }

    hwXQoSAtmPvcDiffDomainRowStatus OBJECT-TYPE
        SYNTAX RowStatus
        MAX-ACCESS read-create
        STATUS current
        DESCRIPTION
            "RowStatus. Three actions are used: active,
            createAndGo, destroy"
        ::= { hwXQoSAtmPvcDiffDomainEntry 5 }

--    trust upstream on atm pvp
  hwXQoSAtmPvpDiffDomainTable OBJECT-TYPE
        SYNTAX SEQUENCE OF HwXQoSAtmPvpDiffDomainEntry
        MAX-ACCESS not-accessible
        STATUS current
        DESCRIPTION
            "Trust diff-serve domain."
        ::= { hwXQoSBaObjects 13 }

    hwXQoSAtmPvpDiffDomainEntry OBJECT-TYPE
        SYNTAX HwXQoSAtmPvpDiffDomainEntry
        MAX-ACCESS not-accessible
        STATUS current
        DESCRIPTION
            "Policy applied on pvp interface Configuration Information Entry."
        INDEX { hwXQoSAtmPvpDiffDomainIfIndex, hwXQoSAtmPvpVpi}
        ::= { hwXQoSAtmPvpDiffDomainTable 1 }

    HwXQoSAtmPvpDiffDomainEntry ::=
        SEQUENCE {
            hwXQoSAtmPvpDiffDomainIfIndex
                Integer32,
            hwXQoSAtmPvpVpi
                Integer32,
            hwXQoSAtmPvpDiffDomainName
                OCTET STRING,
            hwXQoSAtmPvpDiffDomainRowStatus
                RowStatus
         }

    hwXQoSAtmPvpDiffDomainIfIndex OBJECT-TYPE
        SYNTAX Integer32
        MAX-ACCESS read-only
        STATUS current
        DESCRIPTION
            "Atm Interface Index."
        ::= { hwXQoSAtmPvpDiffDomainEntry 1 }

    hwXQoSAtmPvpVpi OBJECT-TYPE
        SYNTAX Integer32
        MAX-ACCESS read-only
        STATUS current
        DESCRIPTION
            "Atm Pvp Vpi"
        ::= { hwXQoSAtmPvpDiffDomainEntry 2 }

    hwXQoSAtmPvpDiffDomainName OBJECT-TYPE
        SYNTAX OCTET STRING (SIZE (1..31))
        MAX-ACCESS read-create
        STATUS current
        DESCRIPTION
            "Name of diff-serve domain."
        ::= { hwXQoSAtmPvpDiffDomainEntry 3 }

    hwXQoSAtmPvpDiffDomainRowStatus OBJECT-TYPE
        SYNTAX RowStatus
        MAX-ACCESS read-create
        STATUS current
        DESCRIPTION
            "RowStatus. Three actions are used: active,
            createAndGo, destroy"
        ::= { hwXQoSAtmPvpDiffDomainEntry 4 }

        -- inbound in diff domain
    hwXQoSBaPhbCfgInfoTable OBJECT-TYPE
        SYNTAX SEQUENCE OF HwXQoSBaPhbCfgInfoEntry
        MAX-ACCESS not-accessible
        STATUS current
        DESCRIPTION
            "A table of diff-serve domain 8021p/Dscp/Exp/IpPri/hqosVlan8021p/hqosDscp/hqosMplsExp/hqosIpPri phb configuration information."
        ::= { hwXQoSBaObjects 14 }

    hwXQoSBaPhbCfgInfoEntry OBJECT-TYPE
        SYNTAX HwXQoSBaPhbCfgInfoEntry
        MAX-ACCESS not-accessible
        STATUS current
        DESCRIPTION
            "Diff-serve domain 8021p/Dscp/Exp/IpPri/hqosVlan8021p/hqosDscp/hqosMplsExp/hqosIpPri phb Configuration Information Entry."
        INDEX { hwXQoSBaIndex, hwXQoSBaPhbType, hwXQoSBaPhbPri }
        ::= { hwXQoSBaPhbCfgInfoTable 1 }

    HwXQoSBaPhbCfgInfoEntry ::=
        SEQUENCE {
            hwXQoSBaPhbType
                BaType,
            hwXQoSBaPhbPri
                Integer32,
            hwXQoSBaPhbCos
                Integer32,
            hwXQoSBaPhbColour
                INTEGER,
            hwXQoSBaPhbRowStatus
                RowStatus
         }

    hwXQoSBaPhbType OBJECT-TYPE
        SYNTAX BaType
        MAX-ACCESS not-accessible
        STATUS current
        DESCRIPTION
            " 8021p (1),
            dscp (2),
            mplsExp(3),
            ipPri(4),
            hqosVlan8021p(5),
            hqosDscp(6),
            hqosMplsExp(7),
            hqosIpPri(8),
            vlan8021pInbound(9)."

            ::= { hwXQoSBaPhbCfgInfoEntry 1 }

    hwXQoSBaPhbPri OBJECT-TYPE
        SYNTAX Integer32
        MAX-ACCESS not-accessible
        STATUS current
        DESCRIPTION
            "8021p / Dscp/Exp / IpPri / hqosVlan8021p / hqosDscp / hqosMplsExp / hqosIpPri."
        ::= { hwXQoSBaPhbCfgInfoEntry 2 }

    hwXQoSBaPhbCos OBJECT-TYPE
        SYNTAX Integer32
        MAX-ACCESS read-create
        STATUS current
        DESCRIPTION
            "Cos of 8021p / Dscp / Exp / IpPri / hqosVlan8021p / hqosDscp / hqosMplsExp / hqosIpPri."
        ::= { hwXQoSBaPhbCfgInfoEntry 3 }

    hwXQoSBaPhbColour OBJECT-TYPE
        SYNTAX INTEGER
        {
            green(1),
            yellow(2),
            red(3)
        }
        MAX-ACCESS read-create
        STATUS current
        DESCRIPTION
            "Colour of 8021p/Dscp/Exp/IpPri/hqosVlan8021p/hqosDscp/hqosMplsExp/hqosIpPri."
        ::= { hwXQoSBaPhbCfgInfoEntry 4 }

    hwXQoSBaPhbRowStatus OBJECT-TYPE
        SYNTAX RowStatus
        MAX-ACCESS read-create
        STATUS current
        DESCRIPTION
            "RowStatus. Three actions are used: active,
            createAndGo, destroy"
        ::= { hwXQoSBaPhbCfgInfoEntry 5 }

    -- outbound in diff domain
    hwXQoSBaMapCfgInfoTable OBJECT-TYPE
        SYNTAX SEQUENCE OF HwXQoSBaMapCfgInfoEntry
        MAX-ACCESS not-accessible
        STATUS current
        DESCRIPTION
            "A table of diff-serve domain 8021p/Dscp/Exp/IpPri/hqosVlan8021p/hqosDscp/hqosMplsExp/hqosIpPri map configuration information."
        ::= { hwXQoSBaObjects 15 }

    hwXQoSBaMapCfgInfoEntry OBJECT-TYPE
        SYNTAX HwXQoSBaMapCfgInfoEntry
        MAX-ACCESS not-accessible
        STATUS current
        DESCRIPTION
            "Diff-serve domain 8021p/Dscp/Exp/IpPri/hqosVlan8021p/hqosDscp/hqosMplsExp/hqosIpPri map Configuration Information Entry."
        INDEX { hwXQoSBaIndex,hwXQoSBaMapType,hwXQoSBaMapCos,hwXQoSBaMapColour }
        ::= { hwXQoSBaMapCfgInfoTable 1 }

    HwXQoSBaMapCfgInfoEntry ::=
        SEQUENCE {
            hwXQoSBaMapType
                BaType,
            hwXQoSBaMapCos
                Integer32,
            hwXQoSBaMapColour
                INTEGER,
            hwXQoSBaMapPri
                Integer32,
            hwXQoSBaMapRowStatus
                RowStatus
            }

    hwXQoSBaMapType OBJECT-TYPE
        SYNTAX BaType
        MAX-ACCESS not-accessible
        STATUS current
        DESCRIPTION
            " 8021p (1),
            dscp (2),
            mplsExp(3),
            ipPri(4),
            hqosVlan8021p(5),
            hqosDscp(6),
            hqosMplsExp(7),
            hqosIpPri(8)."
        ::= { hwXQoSBaMapCfgInfoEntry 1 }

    hwXQoSBaMapCos OBJECT-TYPE
        SYNTAX Integer32
        MAX-ACCESS not-accessible
        STATUS current
        DESCRIPTION
            "Cos of 8021p/Dscp/Exp/IpPri/hqosVlan8021p/hqosDscp/hqosMplsExp/hqosIpPri."
        ::= { hwXQoSBaMapCfgInfoEntry 2 }

    hwXQoSBaMapColour OBJECT-TYPE
        SYNTAX INTEGER
        {
            green(1),
            yellow(2),
            red(3)
        }
        MAX-ACCESS  not-accessible
        STATUS current
        DESCRIPTION
            "Colour of 8021p/Dscp/Exp/IpPri/hqosVlan8021p/hqosDscp/hqosMplsExp/hqosIpPri."
        ::= { hwXQoSBaMapCfgInfoEntry 3 }

    hwXQoSBaMapPri OBJECT-TYPE
        SYNTAX Integer32
        MAX-ACCESS read-create
        STATUS current
        DESCRIPTION
            "8021p/Dscp/Exp/IpPri/hqosVlan8021p/hqosDscp/hqosMplsExp/hqosIpPri."
        ::= { hwXQoSBaMapCfgInfoEntry 4 }

    hwXQoSBaMapRowStatus OBJECT-TYPE
        SYNTAX RowStatus
        MAX-ACCESS read-create
        STATUS current
        DESCRIPTION
            "RowStatus. Three actions are used: active,
            createAndGo, destroy"
        ::= { hwXQoSBaMapCfgInfoEntry 5 }

    hwXQoSIfTrustTable OBJECT-TYPE
        SYNTAX SEQUENCE OF HwXQoSIfTrustEntry
        MAX-ACCESS not-accessible
        STATUS current
        DESCRIPTION
            "Trust diff-serve domain."
        ::= { hwXQoSBaObjects 16 }

    hwXQoSIfTrustEntry OBJECT-TYPE
        SYNTAX HwXQoSIfTrustEntry
        MAX-ACCESS not-accessible
        STATUS current
        DESCRIPTION
            "Policy applied on interface Configuration Information Entry."
        INDEX { hwXQoSIfTrustIfIndex, hwXQoSIfTrustVlanID1, hwXQoSIfTrustVlanID2, hwXQoSBaType }
        ::= { hwXQoSIfTrustTable 1 }

    HwXQoSIfTrustEntry ::=
        SEQUENCE {
            hwXQoSIfTrustIfIndex
                Integer32,
            hwXQoSIfTrustVlanID1
                Integer32,
            hwXQoSIfTrustVlanID2
                Integer32,
            hwXQoSBaType
                BaType,
            hwXQoSIfTrustAction
                INTEGER,
            hwXQoSIfTrustRowStatus
                RowStatus
            }

    hwXQoSIfTrustIfIndex OBJECT-TYPE
        SYNTAX Integer32
        MAX-ACCESS not-accessible
        STATUS current
        DESCRIPTION
            "Interface Index, equal to ifIndex."
        ::= { hwXQoSIfTrustEntry 1 }

    hwXQoSIfTrustVlanID1 OBJECT-TYPE
        SYNTAX Integer32 (0 | 1..4095)
        MAX-ACCESS not-accessible
        STATUS current
        DESCRIPTION
            "start Vlan ID.
            -1 can't be set.
            0 is the default value"
        ::= { hwXQoSIfTrustEntry 2 }

    hwXQoSIfTrustVlanID2 OBJECT-TYPE
        SYNTAX Integer32 (0 | 1..4095)
        MAX-ACCESS not-accessible
        STATUS current
        DESCRIPTION
            "end Vlan ID.
            -1 can't be set.
            0 is the default value"
        ::= { hwXQoSIfTrustEntry 3 }

    hwXQoSBaType OBJECT-TYPE
        SYNTAX BaType
        MAX-ACCESS not-accessible
        STATUS current
        DESCRIPTION
            "vlan8021p (1),
            dscp (2),
            mplsExp(3),
            ipPri(4)"
        ::= { hwXQoSIfTrustEntry 4 }

        hwXQoSIfTrustAction OBJECT-TYPE
        SYNTAX INTEGER {
            distrust(1),
            trust(2)
            }
        MAX-ACCESS read-create
        STATUS current
        DESCRIPTION
            "The trust 802.1p action "
        ::= { hwXQoSIfTrustEntry 5 }

    hwXQoSIfTrustRowStatus OBJECT-TYPE
        SYNTAX RowStatus
        MAX-ACCESS read-create
        STATUS current
        DESCRIPTION
            "RowStatus. Three actions are used: active,
            createAndGo, destroy"
        ::= { hwXQoSIfTrustEntry 6 }

    hwXQoSDeiTable OBJECT-TYPE
        SYNTAX SEQUENCE OF HwXQoSDeiEntry
        MAX-ACCESS not-accessible
        STATUS current
        DESCRIPTION
            "Enable dei."
        ::= { hwXQoSBaObjects 17 }

    hwXQoSDeiEntry OBJECT-TYPE
        SYNTAX HwXQoSDeiEntry
        MAX-ACCESS not-accessible
        STATUS current
        DESCRIPTION
            "Policy applied on interface Configuration Information Entry."
        INDEX { hwXQoSDeiIfIndex, hwXQoSDeiVlanID1,hwXQoSDeiVlanID2 }
        ::= { hwXQoSDeiTable 1 }

    HwXQoSDeiEntry ::=
        SEQUENCE {
            hwXQoSDeiIfIndex
                Integer32,
            hwXQoSDeiVlanID1
                Integer32,
            hwXQoSDeiVlanID2
                Integer32,
            hwXQoSIfEnableDeiAction
                INTEGER,
            hwXQoSDeiRowStatus
                RowStatus
            }

    hwXQoSDeiIfIndex OBJECT-TYPE
        SYNTAX Integer32
        MAX-ACCESS not-accessible
        STATUS current
        DESCRIPTION
            "Interface Index, equal to ifIndex."
        ::= { hwXQoSDeiEntry 1 }

    hwXQoSDeiVlanID1 OBJECT-TYPE
        SYNTAX Integer32 (0 | 1..4095)
        MAX-ACCESS not-accessible
        STATUS current
        DESCRIPTION
            "start Vlan ID.
            -1 can't be set.
            0 is the default value"
        ::= { hwXQoSDeiEntry 2 }

    hwXQoSDeiVlanID2 OBJECT-TYPE
        SYNTAX Integer32 (0 | 1..4095)
        MAX-ACCESS not-accessible
        STATUS current
        DESCRIPTION
            "end Vlan ID.
            -1 can't be set.
            0 is the default value"
        ::= { hwXQoSDeiEntry 3 }

    hwXQoSIfEnableDeiAction OBJECT-TYPE
        SYNTAX INTEGER {
            enabled(1),
            unenabled(2)
        }
        MAX-ACCESS read-create
        STATUS current
        DESCRIPTION
            " The enable dei action
            enabled(1),
            unenabled(2)"
        ::= { hwXQoSDeiEntry 4 }

    hwXQoSDeiRowStatus OBJECT-TYPE
        SYNTAX RowStatus
        MAX-ACCESS read-create
        STATUS current
        DESCRIPTION
            "RowStatus. Three actions are used: active,
            createAndGo, destroy"
        ::= { hwXQoSDeiEntry 5 }

    hwXQoSRemarkTable OBJECT-TYPE
        SYNTAX SEQUENCE OF HwXQoSRemarkEntry
        MAX-ACCESS not-accessible
        STATUS current
        DESCRIPTION
            "Enable Remark."
        ::= { hwXQoSBaObjects 18 }

    hwXQoSRemarkEntry OBJECT-TYPE
        SYNTAX HwXQoSRemarkEntry
        MAX-ACCESS not-accessible
        STATUS current
        DESCRIPTION
            "Policy applied on interface Configuration Information Entry."
        INDEX { hwXQoSRemarkIfIndex, hwXQoSRemarkVlanID1,hwXQoSRemarkVlanID2 }
        ::= { hwXQoSRemarkTable 1 }

    HwXQoSRemarkEntry ::=
        SEQUENCE {
            hwXQoSRemarkIfIndex
                Integer32,
            hwXQoSRemarkVlanID1
                Integer32,
            hwXQoSRemarkVlanID2
                Integer32,
            hwXQoSIfEnableRemarkAction
                INTEGER,
            hwXQoSRemarkRowStatus
                RowStatus
            }

    hwXQoSRemarkIfIndex OBJECT-TYPE
        SYNTAX Integer32
        MAX-ACCESS not-accessible
        STATUS current
        DESCRIPTION
            "Interface Index, equal to ifIndex."
        ::= { hwXQoSRemarkEntry 1 }

    hwXQoSRemarkVlanID1 OBJECT-TYPE
        SYNTAX Integer32 (0 | 1..4094)
        MAX-ACCESS not-accessible
        STATUS current
        DESCRIPTION
            "start Vlan ID.
            -1 can't be set.
            0 is the default value"
        ::= { hwXQoSRemarkEntry 2 }

    hwXQoSRemarkVlanID2 OBJECT-TYPE
        SYNTAX Integer32 (0 | 1..4094)
        MAX-ACCESS not-accessible
        STATUS current
        DESCRIPTION
            "end Vlan ID.
            -1 can't be set.
            0 is the default value"
        ::= { hwXQoSRemarkEntry 3 }

    hwXQoSIfEnableRemarkAction OBJECT-TYPE
        SYNTAX INTEGER {
            enabled(1),
            unenabled(2)
        }
        MAX-ACCESS read-create
        STATUS current
        DESCRIPTION
            " The enable remark action
            enabled(1),
            unenabled(2)"
        ::= { hwXQoSRemarkEntry 4 }

    hwXQoSRemarkRowStatus OBJECT-TYPE
        SYNTAX RowStatus
        MAX-ACCESS read-create
        STATUS current
        DESCRIPTION
            "RowStatus. Three actions are used: active,
            createAndGo, destroy"
        ::= { hwXQoSRemarkEntry 5 }

--   phb enable command begin
    hwXQoSPhbEnableTable OBJECT-TYPE
        SYNTAX SEQUENCE OF HwXQoSPhbEnableEntry
        MAX-ACCESS not-accessible
        STATUS current
        DESCRIPTION
            "PHB enable table."
        ::= { hwXQoSBaObjects 19 }

    hwXQoSPhbEnableEntry OBJECT-TYPE
        SYNTAX HwXQoSPhbEnableEntry
        MAX-ACCESS not-accessible
        STATUS current
        DESCRIPTION
            "A table of diff-serve domain phb enable information."
        INDEX { hwXQoSPhbEnableIfIndex,hwXQoSPhbEnableVlanID1,hwXQoSPhbEnableVlanID2 }
        ::= { hwXQoSPhbEnableTable 1 }

    HwXQoSPhbEnableEntry ::=
        SEQUENCE {
            hwXQoSPhbEnableIfIndex
                Integer32,
            hwXQoSPhbEnableVlanID1
                Integer32,
            hwXQoSPhbEnableVlanID2
                Integer32,
            hwXQoSPhbEnableRowStatus
                RowStatus
            }

    hwXQoSPhbEnableIfIndex OBJECT-TYPE
        SYNTAX Integer32
        MAX-ACCESS not-accessible
        STATUS current
        DESCRIPTION
            "Interface Index, equal to ifIndex."
        ::= { hwXQoSPhbEnableEntry 1 }

    hwXQoSPhbEnableVlanID1 OBJECT-TYPE
        SYNTAX Integer32 (0 | 1..4094)
        MAX-ACCESS not-accessible
        STATUS current
        DESCRIPTION
            "start Vlan ID.
            -1 can't be set.
            0 is the default value"
        ::= { hwXQoSPhbEnableEntry 2 }

    hwXQoSPhbEnableVlanID2 OBJECT-TYPE
        SYNTAX Integer32 (0 | 1..4094)
        MAX-ACCESS not-accessible
        STATUS current
        DESCRIPTION
            "end Vlan ID.
            -1 can't be set.
            0 is the default value"
        ::= { hwXQoSPhbEnableEntry 3 }

    hwXQoSPhbEnableRowStatus OBJECT-TYPE
        SYNTAX RowStatus
        MAX-ACCESS read-create
        STATUS current
        DESCRIPTION
            "RowStatus. Three actions are used: active,
            createAndGo, destroy"
        ::= { hwXQoSPhbEnableEntry 4 }
--   phb enable command end

-- ******************************************************************
--
--   hwXQoSCommonInboundTable
--
-- ******************************************************************

    hwXQoSCommonInboundTable OBJECT-TYPE
        SYNTAX      SEQUENCE OF HwXQoSCommonInboundEntry
        MAX-ACCESS  not-accessible
        STATUS      current
        DESCRIPTION
            " This table is used to configure mapping between the 802.1p priorities or the Differentiated Services
            CodePoint (DSCP) values of upstream packets in the current QinQ domain and service classes. "
        ::= { hwXQoSBaObjects 20 }


    hwXQoSCommonInboundEntry OBJECT-TYPE
        SYNTAX HwXQoSCommonInboundEntry
        MAX-ACCESS not-accessible
        STATUS current
        DESCRIPTION
            " This table is used to configure mapping between the 802.1p priorities or the Differentiated Services
            CodePoint (DSCP) values of upstream packets in the current QinQ domain and service classes. "
        INDEX  { hwXQoSBaIndex, hwXQoSCommonInboundPhbIndex }
        ::= { hwXQoSCommonInboundTable 1 }

    HwXQoSCommonInboundEntry ::=
    SEQUENCE {
            hwXQoSCommonInboundPhbIndex
                Integer32,
            hwXQoSCommonInboundPhbCos
                INTEGER,
            hwXQoSCommonInboundPhbColor
                INTEGER,
            hwXQoSCommonInboundPhbPri
                Integer32,
            hwXQoSCommonInboundRowStatus
                RowStatus
    }

    hwXQoSCommonInboundPhbIndex OBJECT-TYPE
        SYNTAX Integer32
        MAX-ACCESS read-only
        STATUS current
        DESCRIPTION
        " This object indicates a PHB index. "
        ::= { hwXQoSCommonInboundEntry 1 }


    hwXQoSCommonInboundPhbCos OBJECT-TYPE
        SYNTAX INTEGER
        {
            be(1),
            af1(2),
            af2(3),
            af3(4),
            af4(5),
            ef(6),
            cs6(7),
            cs7(8)
        }

        MAX-ACCESS read-create
        STATUS current
        DESCRIPTION
        " This object indicates the 802.1p priority or the DSCP value."
        ::= { hwXQoSCommonInboundEntry 2 }


    hwXQoSCommonInboundPhbColor OBJECT-TYPE
        SYNTAX INTEGER
        {
            green(1),
            yellow(2),
            red(3)
        }
        MAX-ACCESS read-create
        STATUS current
        DESCRIPTION
        " This object indicates the color for marking a type of packets.
            The value can be:
            1: Green
            2: Yellow
            3: Red
        "

        ::= { hwXQoSCommonInboundEntry 3 }

    hwXQoSCommonInboundPhbPri OBJECT-TYPE
        SYNTAX Integer32 (0..7)
        MAX-ACCESS read-only
        STATUS current
        DESCRIPTION
        " The value of this object identifies the CoS.
            The value ranges from 0 to 7.
        "

        ::= { hwXQoSCommonInboundEntry 4 }


    hwXQoSCommonInboundRowStatus OBJECT-TYPE
        SYNTAX RowStatus
        MAX-ACCESS read-create
        STATUS current
        DESCRIPTION
        "This object indicates the row status.Currently, three row statuses are supported: Active, CreateAndGo, and Destroy. "

        ::= { hwXQoSCommonInboundEntry 50 }

-- ******************************************************************
--
--   hwXQoSPppInboundTable
--
-- ******************************************************************
    hwXQoSPppInboundTable OBJECT-TYPE
        SYNTAX      SEQUENCE OF HwXQoSPppInboundEntry
        MAX-ACCESS  not-accessible
        STATUS      current
        DESCRIPTION
            " This table is used to map the priorities of PPP packets to the internal precedence of a router. "
        ::= { hwXQoSBaObjects 21 }


    hwXQoSPppInboundEntry OBJECT-TYPE
        SYNTAX HwXQoSPppInboundEntry
        MAX-ACCESS not-accessible
        STATUS current
        DESCRIPTION
            " This table is used to map the priorities of PPP packets to the internal precedence of a router. "
        INDEX  { hwXQoSBaIndex }
        ::= { hwXQoSPppInboundTable 1 }

    HwXQoSPppInboundEntry ::=
    SEQUENCE {
            hwXQoSPppInboundCos
                INTEGER,
            hwXQoSPppInboundColor
                INTEGER,
            hwXQoSPppInboundRowStatus
                RowStatus
    }

    hwXQoSPppInboundCos OBJECT-TYPE
        SYNTAX INTEGER
        {
            be(1),
            af1(2),
            af2(3),
            af3(4),
            af4(5),
            ef(6),
            cs6(7),
            cs7(8)
        }
        MAX-ACCESS read-create
        STATUS current
        DESCRIPTION
        " This object indicates the CoS of a router.
            The value can be:
        1: BE
        2: AF1
        3. AF2
        4: AF3
        5: AF4
        6: EF
        7: CS6
        8: CS7
        "

        ::= { hwXQoSPppInboundEntry 1 }

    hwXQoSPppInboundColor OBJECT-TYPE
        SYNTAX INTEGER
        {
            green(1),
            yellow(2),
            red(3)
        }
        MAX-ACCESS read-create
        STATUS current
        DESCRIPTION
        " This object indicates the color for marking PPP packets.
            The value can be:
            1: Green
            2: Yellow
            3; Red
        "

        ::= { hwXQoSPppInboundEntry 2 }

    hwXQoSPppInboundRowStatus OBJECT-TYPE
        SYNTAX RowStatus
        MAX-ACCESS read-create
        STATUS current
        DESCRIPTION
        "This object indicates the row status.Currently, three row statuses are supported: Active, CreateAndGo, and Destroy."

        ::= { hwXQoSPppInboundEntry 50 }

-- ******************************************************************
--
--   hwXQoSServiceclassTable
--
-- ******************************************************************

    hwXQoSServiceclassTable OBJECT-TYPE
        SYNTAX      SEQUENCE OF HwXQoSServiceclassEntry
        MAX-ACCESS  not-accessible
        STATUS      current
        DESCRIPTION
            " This table is used to configure upstream traffic to enter specified queues on the interface. "
        ::= { hwXQoSBaObjects 22 }


    hwXQoSServiceclassEntry OBJECT-TYPE
        SYNTAX HwXQoSServiceclassEntry
        MAX-ACCESS not-accessible
        STATUS current
        DESCRIPTION
            " This table is used to configure upstream traffic to enter specified queues on the interface. "
        INDEX  { hwXQoSServiceclassPort }
        ::= { hwXQoSServiceclassTable 1 }

    HwXQoSServiceclassEntry ::=
    SEQUENCE {
            hwXQoSServiceclassPort
                InterfaceIndex,
            hwXQoSServiceclass
                    INTEGER,
            hwXQoSServiceclassRowStatus
                RowStatus
        }

    hwXQoSServiceclassPort OBJECT-TYPE
        SYNTAX InterfaceIndex
        MAX-ACCESS read-only
        STATUS current
        DESCRIPTION
        " This object indicates the interface index."
        ::= { hwXQoSServiceclassEntry 1 }


    hwXQoSServiceclass OBJECT-TYPE
        SYNTAX INTEGER
        {
            be(1),
            af1(2),
            af2(3),
            af3(4),
            af4(5),
            ef(6),
            cs6(7),
            cs7(8)
        }
        MAX-ACCESS read-create
        STATUS current
        DESCRIPTION
        " This object indicates the CoS of the queue that upstream traffic on an interface enters. "
        ::= { hwXQoSServiceclassEntry 2 }


    hwXQoSServiceclassRowStatus OBJECT-TYPE
        SYNTAX RowStatus
        MAX-ACCESS read-create
        STATUS current
        DESCRIPTION
        "This object indicates the row status.Currently, three row statuses are supported: Active, CreateAndGo, and Destroy. "
        ::= { hwXQoSServiceclassEntry 50 }

-- ******************************************************************
--
--   hwXQoSPhbTable
--
-- ******************************************************************

    hwXQoSPhbTable       OBJECT-TYPE
        SYNTAX      SEQUENCE OF HwXQoSPhbEntry
        MAX-ACCESS  not-accessible
        STATUS      current
        DESCRIPTION
            " This table is used to prohibit the function of checking the PHB table on the outgoing interface. "
        ::= { hwXQoSBaObjects 23 }


    hwXQoSPhbEntry OBJECT-TYPE
        SYNTAX HwXQoSPhbEntry
        MAX-ACCESS not-accessible
        STATUS current
        DESCRIPTION
            " This table is used to prohibit the function of checking the PHB table on the outgoing interface. "
        INDEX  { hwXQoSPhbPort }
        ::= { hwXQoSPhbTable 1 }

    HwXQoSPhbEntry ::=
    SEQUENCE {
            hwXQoSPhbPort
                InterfaceIndex,
            hwXQoSPhbEnable
                INTEGER,
            hwXQoSPhbRowStatus
                RowStatus
    }

    hwXQoSPhbPort OBJECT-TYPE
        SYNTAX InterfaceIndex
        MAX-ACCESS read-only
        STATUS current
        DESCRIPTION
        " This object indicates the interface index. "
        ::= { hwXQoSPhbEntry 1 }

    hwXQoSPhbEnable OBJECT-TYPE
        SYNTAX INTEGER
        {
            enable(1),
            disable(2)
        }
        MAX-ACCESS read-create
        STATUS current
        DESCRIPTION
        " This object indicates the CoS of the queue that upstream traffic on an interface enters. "
        DEFVAL {enable}
        ::= { hwXQoSPhbEntry 2 }


    hwXQoSPhbRowStatus OBJECT-TYPE
        SYNTAX RowStatus
        MAX-ACCESS read-create
        STATUS current
        DESCRIPTION
        "This object indicates the row status.Currently, three row statuses are supported: Active, CreateAndGo, and Destroy. "

        ::= { hwXQoSPhbEntry 50 }

-- ******************************************************************
--
--   hwXQoSFieldDeiTable
--
-- ******************************************************************

    hwXQoSFieldDeiTable OBJECT-TYPE
        SYNTAX      SEQUENCE OF HwXQoSFieldDeiEntry
        MAX-ACCESS  not-accessible
        STATUS      current
        DESCRIPTION
            " This table is sued to enable the drop eligible indicator (DEI) capability of the packets
            on an interface and in a specified VLAN range. "
        ::= { hwXQoSBaObjects 24 }

    hwXQoSFieldDeiEntry OBJECT-TYPE
        SYNTAX HwXQoSFieldDeiEntry
        MAX-ACCESS not-accessible
        STATUS current
        DESCRIPTION
            " This table is sued to enable the drop eligible indicator (DEI) capability of the packets
            on an interface and in a specified VLAN range. "
        INDEX  { hwXQoSFieldDeiInterface,hwXQoSFieldDeiVlanId }
        ::= { hwXQoSFieldDeiTable 1 }

    HwXQoSFieldDeiEntry ::=
    SEQUENCE {
            hwXQoSFieldDeiInterface
                InterfaceIndex,
            hwXQoSFieldDeiVlanId
                Integer32,
            hwXQoSFieldDeiEnabled
                Integer32,
            hwXQoSFieldDeiRowStatus
                RowStatus
    }

    hwXQoSFieldDeiInterface OBJECT-TYPE
        SYNTAX InterfaceIndex
        MAX-ACCESS read-only
        STATUS current
        DESCRIPTION
        " This object indicates the interface index. "
        ::= { hwXQoSFieldDeiEntry 1 }

    hwXQoSFieldDeiVlanId OBJECT-TYPE
        SYNTAX Integer32 (1..4094)
        MAX-ACCESS read-only
        STATUS current
        DESCRIPTION
        " The value of this object identifies the VLAN ID.
            The value ranges from 1 to 4094.
        "
        ::= { hwXQoSFieldDeiEntry 2 }

    hwXQoSFieldDeiEnabled OBJECT-TYPE
        SYNTAX Integer32 (0..2)
        MAX-ACCESS read-create
        STATUS current
        DESCRIPTION
        " The value of this object identifies whether to enable the DEI capability of the packets on a VLAN. "
        ::= { hwXQoSFieldDeiEntry 3 }

    hwXQoSFieldDeiRowStatus OBJECT-TYPE
        SYNTAX RowStatus
        MAX-ACCESS read-create
        STATUS current
        DESCRIPTION
        "This object indicates the row status.Currently, three row statuses are supported: Active, CreateAndGo, and Destroy."

        ::= { hwXQoSFieldDeiEntry 50 }

-- ******************************************************************
--
--   hwXQoSPicForwardingTable
--
-- ******************************************************************

    hwXQoSPicForwardingTable OBJECT-TYPE
        SYNTAX      SEQUENCE OF HwXQoSPicForwardingEntry
        MAX-ACCESS  not-accessible
        STATUS      current
        DESCRIPTION
            " hwXQoSPicForwardingTable "
        ::= { hwXQoSBaObjects 25 }

    hwXQoSPicForwardingEntry OBJECT-TYPE
        SYNTAX HwXQoSPicForwardingEntry
        MAX-ACCESS not-accessible
        STATUS current
        DESCRIPTION
            " hwXQoSPicForwardingEntry "
        INDEX  { hwXQoSPicForwardingInterface }
        ::= { hwXQoSPicForwardingTable 1 }

    HwXQoSPicForwardingEntry ::=
    SEQUENCE {
            hwXQoSPicForwardingInterface
                InterfaceIndex,
            hwXQoSPicForwarding8021pValue
                Integer32,
            hwXQoSPicForwardingPriority
                INTEGER,
            hwXQoSPicForwardingRowStatus
                RowStatus
    }

    hwXQoSPicForwardingInterface OBJECT-TYPE
        SYNTAX InterfaceIndex
        MAX-ACCESS read-only
        STATUS current
        DESCRIPTION
        " hwXQoSPicForwardingInterface "
        ::= { hwXQoSPicForwardingEntry 1 }

    hwXQoSPicForwarding8021pValue OBJECT-TYPE
        SYNTAX Integer32 (0..8)
        MAX-ACCESS read-create
        STATUS current
        DESCRIPTION
        " hwXQoSPicForwarding8021pValue "
        ::= { hwXQoSPicForwardingEntry 2 }

    hwXQoSPicForwardingPriority OBJECT-TYPE
        SYNTAX INTEGER
        {
            high(1)
        }
        MAX-ACCESS read-create
        STATUS current
        DESCRIPTION
        " hwXQoSPicForwardingPriority "
        ::= { hwXQoSPicForwardingEntry 3 }

    hwXQoSPicForwardingRowStatus OBJECT-TYPE
        SYNTAX RowStatus
        MAX-ACCESS read-create
        STATUS current
        DESCRIPTION
        "
        Row status. The value ranges from 1 to 6 but usually 4 and 6 are used.
        createAndGo[4] - create a row.
        destroy[6] -delete a row.
        "

    ::= { hwXQoSPicForwardingEntry 4 }

-- ******************************************************************
--
--   hwXQoSCarTable
--
-- ******************************************************************

    hwXQoSCarTable OBJECT-TYPE
        SYNTAX      SEQUENCE OF HwXQoSCarEntry
        MAX-ACCESS  not-accessible
        STATUS      current
        DESCRIPTION
            " This table is used to configure traffic policing on a Layer 3 main interface or a Layer 2 interface. "
        ::= { hwXQoSBaObjects 26 }

    hwXQoSCarEntry OBJECT-TYPE
        SYNTAX HwXQoSCarEntry
        MAX-ACCESS not-accessible
        STATUS current
        DESCRIPTION
            " This table is used to configure traffic policing on a Layer 3 main interface or a Layer 2 interface. "
        INDEX  { hwXQoSCarInterfaceIndex,hwXQoSCarDirection,hwXQoSCarVlanID }
        ::= { hwXQoSCarTable 1 }

    HwXQoSCarEntry ::=
        SEQUENCE {
            hwXQoSCarInterfaceIndex
                InterfaceIndex,
            hwXQoSCarDirection
                INTEGER,
            hwXQoSCarVlanID
                Integer32,
            hwXQoSCarCirValue
                Integer32,
            hwXQoSCarPirValue
                Integer32,
            hwXQoSCarCbsValue
                Integer32,
            hwXQoSCarPbsValue
                Integer32,
            hwXQoSCarGreenAction
                INTEGER,
            hwXQoSCarGreenServiceClass
                INTEGER,
            hwXQoSCarGreenColor
                INTEGER,
            hwXQoSCarYellowAction
                INTEGER,
            hwXQoSCarYellowServiceClass
                INTEGER,
            hwXQoSCarYellowColor
                INTEGER,
            hwXQoSCarRedAction
                INTEGER,
            hwXQoSCarRedServiceClass
                INTEGER,
            hwXQoSCarRedColor
                INTEGER,
            hwXQoSCarRowStatus
                RowStatus,
            hwXQoSCarCirValueEx
                Unsigned32,
            hwXQoSCarPirValueEx
                Unsigned32,
            hwXQoSCarCbsValueEx
                Unsigned32,
            hwXQoSCarPbsValueEx
                Unsigned32
        }

    hwXQoSCarInterfaceIndex OBJECT-TYPE
        SYNTAX InterfaceIndex
        MAX-ACCESS read-only
        STATUS current
        DESCRIPTION
            " This object indicates the interface index."
        ::= { hwXQoSCarEntry 1 }

    hwXQoSCarDirection OBJECT-TYPE
        SYNTAX INTEGER
        {
            inbound(1),
            outbound(2)
        }
        MAX-ACCESS read-only
        STATUS current
        DESCRIPTION
            " This object indicates the traffic direction to which CAR applies on an interface.
            The value can be one of the following:
            (1)Inbound
            (2)outbound."
        ::= { hwXQoSCarEntry 2 }

    hwXQoSCarVlanID OBJECT-TYPE
        SYNTAX Integer32 (1..4094)
        MAX-ACCESS read-only
        STATUS current
        DESCRIPTION
            " This object indicates the value of VLAN ID.
        The value ranges from 1 to 4094. "
        ::= { hwXQoSCarEntry 3 }

    hwXQoSCarCirValue OBJECT-TYPE
        SYNTAX Integer32 (0..100000000)
        MAX-ACCESS read-create
        STATUS current
        DESCRIPTION
            " The value of this object identifies the CIR on an interface."
        ::= { hwXQoSCarEntry 4 }

    hwXQoSCarPirValue OBJECT-TYPE
        SYNTAX Integer32  (-1 | 0..100000000)
        MAX-ACCESS read-create
        STATUS current
        DESCRIPTION
            " The value of this object identifies the PIR on an interface."
        ::= { hwXQoSCarEntry 5 }

    hwXQoSCarCbsValue OBJECT-TYPE
        SYNTAX Integer32 (0..100000000)
        MAX-ACCESS read-create
        STATUS current
        DESCRIPTION
            " The value of this object identifies the CBS on an interface."
        ::= { hwXQoSCarEntry 6 }

    hwXQoSCarPbsValue OBJECT-TYPE
        SYNTAX Integer32 (0..100000000)
        MAX-ACCESS read-create
        STATUS current
        DESCRIPTION
            " The value of this object identifies the PBS on an interface."
        ::= { hwXQoSCarEntry 7 }

    hwXQoSCarGreenAction OBJECT-TYPE
        SYNTAX INTEGER
        {
            pass(1),
            discard(2),
            null(3)
        }
        MAX-ACCESS read-create
        STATUS current
        DESCRIPTION
            " This object indicates the action for packets marked green."
        ::= { hwXQoSCarEntry 8 }

    hwXQoSCarGreenServiceClass OBJECT-TYPE
        SYNTAX INTEGER
        {
            be(1),
            af1(2),
            af2(3),
            af3(4),
            af4(5),
            ef(6),
            cs6(7),
            cs7(8),
            null(9)
        }
        MAX-ACCESS read-create
        STATUS current
        DESCRIPTION
            " This object indicates the service class of the packets marked in green. The value can be one of the following:
            1: BE
            2: AF1
            3. AF2
            4: AF3
            5: AF4
            6: EF
            7: CS6
            8: CS7
            9: null."
        ::= { hwXQoSCarEntry 9 }

    hwXQoSCarGreenColor OBJECT-TYPE
        SYNTAX INTEGER
        {
            green(1),
            yellow(2),
            red(3),
            null(4)
        }
        MAX-ACCESS read-create
        STATUS current
        DESCRIPTION
            " This object indicates the color that green packets are to be re-marked. The value can be one of the following:
            1: green
            2: yellow
            3: red
            4: null."
        ::= { hwXQoSCarEntry 10 }

    hwXQoSCarYellowAction OBJECT-TYPE
        SYNTAX INTEGER
        {
            pass(1),
            discard(2),
            null(3)
        }
        MAX-ACCESS read-create
        STATUS current
        DESCRIPTION
            " This object indicates the action for packets marked yellow."
        ::= { hwXQoSCarEntry 11 }

    hwXQoSCarYellowServiceClass OBJECT-TYPE
        SYNTAX INTEGER
        {
            be(1),
            af1(2),
            af2(3),
            af3(4),
            af4(5),
            ef(6),
            cs6(7),
            cs7(8),
            null(9)
        }
        MAX-ACCESS read-create
        STATUS current
        DESCRIPTION
            " This object indicates the service class of the packets marked yellow. The value can be one of the following:
        1: BE
        2: AF1
        3. AF2
        4: AF3
        5: AF4
        6: EF
        7: CS6
        8: CS7
        9: null."

        ::= { hwXQoSCarEntry 12 }

    hwXQoSCarYellowColor OBJECT-TYPE
        SYNTAX INTEGER
        {
            green(1),
            yellow(2),
            red(3),
            null(4)
        }
        MAX-ACCESS read-create
        STATUS current
        DESCRIPTION
            " This object indicates the color that yellow packets are to be re-marked. The value can be one of the following:
            1: green
            2: yellow
            3: red
            4: null."
        ::= { hwXQoSCarEntry 13 }

    hwXQoSCarRedAction OBJECT-TYPE
        SYNTAX INTEGER
        {
            pass(1),
            discard(2),
            null(3)
        }
        MAX-ACCESS read-create
        STATUS current
        DESCRIPTION
            " This object indicates the action for packets marked red. "
        DEFVAL {discard}
        ::= { hwXQoSCarEntry 14 }

    hwXQoSCarRedServiceClass OBJECT-TYPE
        SYNTAX INTEGER
        {
            be(1),
            af1(2),
            af2(3),
            af3(4),
            af4(5),
            ef(6),
            cs6(7),
            cs7(8),
            null(9)
        }
        MAX-ACCESS read-create
        STATUS current
        DESCRIPTION
            "This object indicates the service class of the packets marked red. The value can be one of the following:
            1: BE
            2: AF1
            3. AF2
            4: AF3
            5: AF4
            6: EF
            7: CS6
            8: CS7
            9: null."
        ::= { hwXQoSCarEntry 15 }

    hwXQoSCarRedColor OBJECT-TYPE
        SYNTAX INTEGER
        {
            green(1),
            yellow(2),
            red(3),
            null(4)
        }
        MAX-ACCESS read-create
        STATUS current
        DESCRIPTION
            " This object indicates the color that red packets are to be re-marked. The value can be one of the following:
            1: green
            2: yellow
            3: red
            4: null. "
        ::= { hwXQoSCarEntry 16 }

    hwXQoSCarRowStatus OBJECT-TYPE
        SYNTAX RowStatus
        MAX-ACCESS read-create
        STATUS current
        DESCRIPTION
            "This object indicates the CAR status."

    ::= { hwXQoSCarEntry 50 }

    hwXQoSCarCirValueEx OBJECT-TYPE
        SYNTAX Unsigned32
        MAX-ACCESS read-create
        STATUS current
        DESCRIPTION
            "This object indicates the CIR of an interface."
        ::= { hwXQoSCarEntry 51 }

    hwXQoSCarPirValueEx OBJECT-TYPE
        SYNTAX Unsigned32
        MAX-ACCESS read-create
        STATUS current
        DESCRIPTION
            " This object indicates the PIR of an interface."
        ::= { hwXQoSCarEntry 52 }

    hwXQoSCarCbsValueEx OBJECT-TYPE
        SYNTAX Unsigned32
        MAX-ACCESS read-create
        STATUS current
        DESCRIPTION
            " This object indicates the CBS of an interface."
        ::= { hwXQoSCarEntry 53 }

    hwXQoSCarPbsValueEx OBJECT-TYPE
        SYNTAX Unsigned32
        MAX-ACCESS read-create
        STATUS current
        DESCRIPTION
            " This object indicates the PBS of an interface."
        ::= { hwXQoSCarEntry 54 }

-- ******************************************************************
--
--   hwXQoSPortShapingTable
--
-- ******************************************************************

    hwXQoSPortShapingTable OBJECT-TYPE
        SYNTAX      SEQUENCE OF HwXQoSPortShapingEntry
        MAX-ACCESS  not-accessible
        STATUS      current
        DESCRIPTION
            " This table is used to limit the rate at which the interface sends data. "
        ::= { hwXQoSBaObjects 27 }

    hwXQoSPortShapingEntry OBJECT-TYPE
        SYNTAX HwXQoSPortShapingEntry
        MAX-ACCESS not-accessible
        STATUS current
        DESCRIPTION
            " This table is used to limit the rate at which packets are sent on an interface. "
        INDEX  { hwXQoSPortShapingInterface }
        ::= { hwXQoSPortShapingTable 1 }

    HwXQoSPortShapingEntry ::=
    SEQUENCE {
            hwXQoSPortShapingInterface
                InterfaceIndex,
            hwXQoSPortShapingValue
                OCTET STRING,
            hwXQoSPortShapingPbsValue
                Integer32,
            hwXQoSPortShapPercent
                Integer32,
            hwXQoSPortShapingRowStatus
                RowStatus
    }

    hwXQoSPortShapingInterface OBJECT-TYPE
        SYNTAX InterfaceIndex
        MAX-ACCESS read-only
        STATUS current
        DESCRIPTION
        " This object indicates the interface index."
        ::= { hwXQoSPortShapingEntry 1 }

    hwXQoSPortShapingValue OBJECT-TYPE
        SYNTAX OCTET STRING (SIZE (1..10))
        MAX-ACCESS read-create
        STATUS current
        DESCRIPTION
        " The value of this object identifies the shaping rate.
        The maximum value equals the interface bandwidth.
            0 means not configured shaping rate."
        ::= { hwXQoSPortShapingEntry 2 }

    hwXQoSPortShapingPbsValue OBJECT-TYPE
        SYNTAX Integer32 (1..2147483646)
        MAX-ACCESS read-create
        STATUS current
        DESCRIPTION
        " This object indicates the PBS.
        The value is an integer that ranges from 1 to 2147483646, in bytes.
        the default pbs-value is 131072.
        "
        ::= { hwXQoSPortShapingEntry 3 }

    hwXQoSPortShapPercent OBJECT-TYPE
        SYNTAX Integer32 (0..100)
        MAX-ACCESS read-create
        STATUS current
        DESCRIPTION
        " The percentage-value of this object identifies the shaping rate, 0 means not configured shaping percentage."
        ::= { hwXQoSPortShapingEntry 4 }

    hwXQoSPortShapingRowStatus OBJECT-TYPE
        SYNTAX RowStatus
        MAX-ACCESS read-create
        STATUS current
        DESCRIPTION
        "This object indicates the row status indicator."

    ::= { hwXQoSPortShapingEntry 50 }

-- ******************************************************************
--
--   hwXQoSQueueTable
--
-- ******************************************************************

    hwXQoSQueueTable OBJECT-TYPE
        SYNTAX      SEQUENCE OF HwXQoSQueueEntry
        MAX-ACCESS  not-accessible
        STATUS      current
        DESCRIPTION
            " hwXQoSQueueTable "
        ::= { hwXQoSBaObjects 28 }

    hwXQoSQueueEntry OBJECT-TYPE
        SYNTAX HwXQoSQueueEntry
        MAX-ACCESS not-accessible
        STATUS current
        DESCRIPTION
            " hwXQoSQueueEntry "
        INDEX  { hwXQoSQueueInterfaceIndex }
        ::= { hwXQoSQueueTable 1 }

    HwXQoSQueueEntry ::=
        SEQUENCE {
            hwXQoSQueueInterfaceIndex
                InterfaceIndex,
            hwXQoSQueueServiceClass
                INTEGER,
            hwXQoSQueueCirValue
                Integer32,
            hwXQoSQueueCirPercentage
                Integer32,
            hwXQoSQueueDirection
                INTEGER,
            hwXQoSQueueRowStatus
                RowStatus
        }

    hwXQoSQueueInterfaceIndex OBJECT-TYPE
        SYNTAX InterfaceIndex
        MAX-ACCESS read-only
        STATUS current
        DESCRIPTION
            " hwXQoSQueueInterfaceIndex "
        ::= { hwXQoSQueueEntry 1 }

    hwXQoSQueueServiceClass OBJECT-TYPE
        SYNTAX INTEGER
        {
            be(1),
            af1(2),
            af2(3),
            af3(4),
            af4(5),
            ef(6),
            cs6(7),
            cs7(8)
        }
        MAX-ACCESS read-create
        STATUS current
        DESCRIPTION
            " hwXQoSQueueServiceClass "
        ::= { hwXQoSQueueEntry 2 }


    hwXQoSQueueCirValue OBJECT-TYPE
        SYNTAX Integer32 (0..10000)
        MAX-ACCESS read-create
        STATUS current
        DESCRIPTION
            " hwXQoSQueueCirValue "
        ::= { hwXQoSQueueEntry 3 }


    hwXQoSQueueCirPercentage OBJECT-TYPE
        SYNTAX Integer32 (0..100)
        MAX-ACCESS read-create
        STATUS current
        DESCRIPTION
            " hwXQoSQueueCirPercentage "
        ::= { hwXQoSQueueEntry 4 }

    hwXQoSQueueDirection OBJECT-TYPE
        SYNTAX INTEGER
        {
            inbound(1),
            outbound(2)
        }
        MAX-ACCESS read-create
        STATUS current
        DESCRIPTION
            " hwXQoSQueueDirection "
        ::= { hwXQoSQueueEntry 5 }

    hwXQoSQueueRowStatus OBJECT-TYPE
        SYNTAX RowStatus
        MAX-ACCESS read-create
        STATUS current
        DESCRIPTION
            "Row status. The value ranges from 1 to 6 but usually 4 and 6 are used.
            createAndGo[4] - create a row.
            destroy[6] -delete a row."
        ::= { hwXQoSQueueEntry 6 }

-- ******************************************************************
--
--   hwXQoSCarStatisticsTable
--
-- ******************************************************************

    hwXQoSCarStatisticsTable OBJECT-TYPE
        SYNTAX      SEQUENCE OF HwXQoSCarStatisticsEntry
        MAX-ACCESS  not-accessible
        STATUS      current
        DESCRIPTION
            "This table displays CAR statistics on an interface. "
        ::= { hwXQoSBaObjects 29 }

    hwXQoSCarStatisticsEntry OBJECT-TYPE
        SYNTAX HwXQoSCarStatisticsEntry
        MAX-ACCESS not-accessible
        STATUS current
        DESCRIPTION
            " This table is used to query the CAR statistics on an interface. "
        INDEX  { hwXQoSCarStatisticsInterfaceIndex,hwXQoSCarStatisticsDirection,hwXQoSCarStatisticsVlanid,hwXQoSCarStatisticsSlotNumber}
        ::= { hwXQoSCarStatisticsTable 1 }

    HwXQoSCarStatisticsEntry ::=
        SEQUENCE {
            hwXQoSCarStatisticsInterfaceIndex
                InterfaceIndex,
            hwXQoSCarStatisticsDirection
                INTEGER,
            hwXQoSCarStatisticsVlanid
                Integer32,
            hwXQoSCarStatisticsSlotNumber
                Integer32,
            hwXQoSCarStatisticsReset
                INTEGER,
            hwXQoSCarStatisticsPassPackets
                Counter64,
            hwXQoSCarStatisticsPassBytes
                Counter64,
            hwXQoSCarStatisticsDropPackets
                Counter64,
            hwXQoSCarStatisticsDropBytes
                Counter64,
            hwXQoSCarStatisticsPassPacketsRate
                Counter64,
            hwXQoSCarStatisticsPassBytesRate
                Counter64,
            hwXQoSCarStatisticsDropPacketsRate
                Counter64,
            hwXQoSCarStatisticsDropBytesRate
                Counter64
        }

    hwXQoSCarStatisticsInterfaceIndex OBJECT-TYPE
        SYNTAX InterfaceIndex
        MAX-ACCESS read-only
        STATUS current
        DESCRIPTION
            " This object indicates the interface index."
        ::= { hwXQoSCarStatisticsEntry 1 }

    hwXQoSCarStatisticsDirection OBJECT-TYPE
        SYNTAX INTEGER
        {
            inbound(1),
            outbound(2)
        }
        MAX-ACCESS read-only
        STATUS current
        DESCRIPTION
            "This object indicates the traffic direction to which CAR applies.
            The value can be one of the following:
            inbound(1)
            outbound(2).
            "
        ::= { hwXQoSCarStatisticsEntry 2 }

    hwXQoSCarStatisticsVlanid OBJECT-TYPE
        SYNTAX Integer32 (0..4094)
        MAX-ACCESS read-only
        STATUS current
        DESCRIPTION
            " The value of this object identifies the VLAN ID of an interface where the CAR statistics are queried.
        The value ranges from 1 to 4094. "
        ::= { hwXQoSCarStatisticsEntry 3 }

    hwXQoSCarStatisticsSlotNumber OBJECT-TYPE
        SYNTAX Integer32 (0..128)
        MAX-ACCESS read-only
        STATUS current
        DESCRIPTION
            " This object indicates the ID of the board where CAR statistics are queried.
        The value ranges from 0 to 128. "
        ::= { hwXQoSCarStatisticsEntry 4 }

    hwXQoSCarStatisticsReset OBJECT-TYPE
        SYNTAX INTEGER
        {
            reset(1)
        }
        MAX-ACCESS read-create
        STATUS current
        DESCRIPTION
            " This object indicates the resetting of statistics. "
        ::= { hwXQoSCarStatisticsEntry 5 }

    hwXQoSCarStatisticsPassPackets OBJECT-TYPE
        SYNTAX  Counter64
        MAX-ACCESS read-only
        STATUS current
        DESCRIPTION
            " This object indicates the number of forwarded packets. "
        ::= { hwXQoSCarStatisticsEntry 6 }

    hwXQoSCarStatisticsPassBytes OBJECT-TYPE
        SYNTAX  Counter64
        MAX-ACCESS read-only
        STATUS current
        DESCRIPTION
            " This object indicates the number of passed bytes. "
        ::= { hwXQoSCarStatisticsEntry 7 }

    hwXQoSCarStatisticsDropPackets OBJECT-TYPE
        SYNTAX  Counter64
        MAX-ACCESS read-only
        STATUS current
        DESCRIPTION
            " This object indicates the number of discarded packets. "
        ::= { hwXQoSCarStatisticsEntry 8 }

    hwXQoSCarStatisticsDropBytes OBJECT-TYPE
        SYNTAX  Counter64
        MAX-ACCESS read-only
        STATUS current
        DESCRIPTION
            " This object indicates the number of discarded bytes. "
        ::= { hwXQoSCarStatisticsEntry 9 }

    hwXQoSCarStatisticsPassPacketsRate OBJECT-TYPE
        SYNTAX  Counter64
        MAX-ACCESS read-only
        STATUS current
        DESCRIPTION
            " This object indicates the rate at which packets are forwarded. "
        ::= { hwXQoSCarStatisticsEntry 10 }

    hwXQoSCarStatisticsPassBytesRate  OBJECT-TYPE
        SYNTAX  Counter64
        MAX-ACCESS read-only
        STATUS current
        DESCRIPTION
            " This object indicates the byte pass rate.  "
        ::= { hwXQoSCarStatisticsEntry 11 }

    hwXQoSCarStatisticsDropPacketsRate OBJECT-TYPE
        SYNTAX  Counter64
        MAX-ACCESS read-only
        STATUS current
        DESCRIPTION
            " This object indicates the rate at which packets are discarded. "
        ::= { hwXQoSCarStatisticsEntry 12 }

    hwXQoSCarStatisticsDropBytesRate  OBJECT-TYPE
        SYNTAX  Counter64
        MAX-ACCESS read-only
        STATUS current
        DESCRIPTION
            " This object indicates the byte drop rate.  "
        ::= { hwXQoSCarStatisticsEntry 13 }

-- ******************************************************************
--
--   hwXQoSCpRateLimitTable
--
-- ******************************************************************

    hwXQoSCpRateLimitTable OBJECT-TYPE
        SYNTAX      SEQUENCE OF HwXQoSCpRateLimitEntry
        MAX-ACCESS  not-accessible
        STATUS      current
        DESCRIPTION
            " This table is used to set the limit on the rate at which IGMP packets are transmitted. "
        ::= { hwXQoSBaObjects 30 }

    hwXQoSCpRateLimitEntry OBJECT-TYPE
        SYNTAX HwXQoSCpRateLimitEntry
        MAX-ACCESS not-accessible
        STATUS current
        DESCRIPTION
            " This table is used to set the limit on the rate at which IGMP packets are transmitted. "
        INDEX  { hwXQoSCpRateLimitIfIndex,hwXQoSCpRateLimitPeVidValue,hwXQoSCpRateLimitCeVidBegin}
        ::= { hwXQoSCpRateLimitTable 1 }

    HwXQoSCpRateLimitEntry ::=
        SEQUENCE {
            hwXQoSCpRateLimitIfIndex
                InterfaceIndex,
            hwXQoSCpRateLimitPeVidValue
                Integer32,
            hwXQoSCpRateLimitCeVidBegin
                Integer32,
            hwXQoSCpRateLimitCeVidEnd
                Integer32,
            hwXQoSCpRateLimitType
                INTEGER,
            hwXQoSCpRateLimitIgmpCir
                Integer32,
            hwXQoSCpRateLimitIgmpCbs
                Integer32,
            hwXQoSCpRateLimitRowStatus
                RowStatus
        }

    hwXQoSCpRateLimitIfIndex OBJECT-TYPE
        SYNTAX InterfaceIndex
        MAX-ACCESS read-only
        STATUS current
        DESCRIPTION
            " This object indicates the index of an interface. "
        ::= { hwXQoSCpRateLimitEntry 1 }

    hwXQoSCpRateLimitPeVidValue OBJECT-TYPE
        SYNTAX Integer32 (0..4094)
        MAX-ACCESS read-only
        STATUS current
        DESCRIPTION
            " This object indicates an outer VLAN tag.
        The value ranges from 1 to 4094. "
        ::= { hwXQoSCpRateLimitEntry 2 }

    hwXQoSCpRateLimitCeVidBegin OBJECT-TYPE
        SYNTAX Integer32 (0..4094)
        MAX-ACCESS read-only
        STATUS current
        DESCRIPTION
            " This object indicates the start inner VLAN tag.
        The value ranges from 1 to 4094. "
        ::= { hwXQoSCpRateLimitEntry 3 }

    hwXQoSCpRateLimitCeVidEnd OBJECT-TYPE
        SYNTAX Integer32 (0..4094)
        MAX-ACCESS read-create
        STATUS current
        DESCRIPTION
            " This object indicates the end inner VLAN tag.
        The value ranges from 1 to 4094. "
        ::= { hwXQoSCpRateLimitEntry 4 }

    hwXQoSCpRateLimitType OBJECT-TYPE
        SYNTAX INTEGER
        {
            igmp(1)
        }
        MAX-ACCESS read-create
        STATUS current
        DESCRIPTION
            " The value of this object identifies the type of packets.
                The value can be:
                1: IGMP
            "
        ::= { hwXQoSCpRateLimitEntry 5 }

    hwXQoSCpRateLimitIgmpCir OBJECT-TYPE
        SYNTAX Integer32 (0 | 32..1000000)
        MAX-ACCESS read-create
        STATUS current
        DESCRIPTION
            " This object indicates the packet sending rate.
        The value ranges from 32 to 10000000. "
        ::= { hwXQoSCpRateLimitEntry 6 }

    hwXQoSCpRateLimitIgmpCbs OBJECT-TYPE
        SYNTAX Integer32 (100..33554432)
        MAX-ACCESS read-create
        STATUS current
        DESCRIPTION
            " This object indicates the CBS of the sent packets.
        The value ranges from 100 to 33554432. "
        ::= { hwXQoSCpRateLimitEntry 7 }

    hwXQoSCpRateLimitRowStatus  OBJECT-TYPE
        SYNTAX RowStatus
        MAX-ACCESS read-create
        STATUS current
        DESCRIPTION
            "
            Row status. The value ranges from 1 to 6 but usually 4 and 6 are used.
            createAndGo[4] - create a row.
            destroy[6] -delete a row.
            "
    ::= { hwXQoSCpRateLimitEntry 50 }

-- ******************************************************************
--
--   hwXQoSPortQueueStatisticsTable
--
-- ******************************************************************

    hwXQoSPortQueueStatisticsTable OBJECT-TYPE
        SYNTAX      SEQUENCE OF HwXQoSPortQueueStatisticsEntry
        MAX-ACCESS  not-accessible
        STATUS      current
        DESCRIPTION
            " This table is used to query the statistics of class queues. "
        ::= { hwXQoSBaObjects 31 }

    hwXQoSPortQueueStatisticsEntry OBJECT-TYPE
        SYNTAX HwXQoSPortQueueStatisticsEntry
        MAX-ACCESS not-accessible
        STATUS current
        DESCRIPTION
            " This table is used to query the statistics of class queues. "
        INDEX  { hwXQoSPortQueueStatisticsInterfaceIndex,
                hwXQoSPortQueueStatisticsDirection,
                hwXQoSPortQueueStatisticsQueueIndex }
        ::= { hwXQoSPortQueueStatisticsTable 1 }

    HwXQoSPortQueueStatisticsEntry ::=
        SEQUENCE {
            hwXQoSPortQueueStatisticsInterfaceIndex
                InterfaceIndex,
            hwXQoSPortQueueStatisticsDirection
                INTEGER,
            hwXQoSPortQueueStatisticsQueueIndex
                INTEGER,
            hwXQoSPortQueueStatisticsReset
                INTEGER,
            hwXQoSPortQueueStatisticsTotalPassPackets
                Counter64,
            hwXQoSPortQueueStatisticsTotalPassBytes
                Counter64,
            hwXQoSPortQueueStatisticsTotalDiscardPackets
                Counter64,
            hwXQoSPortQueueStatisticsTotalDiscardBytes
                Counter64,
            hwXQoSPortQueueStatisticsDropTailDiscardPackets
                Counter64,
            hwXQoSPortQueueStatisticsDropTailDiscardBytes
                Counter64,
            hwXQoSPortQueueStatisticsWredDiscardPackets
                Counter64,
            hwXQoSPortQueueStatisticsWredDiscardBytes
                Counter64,
            hwXQoSPortQueueStatisticsPassPacketsRate
                Counter64,
            hwXQoSPortQueueStatisticsPassBytesRate
                Counter64,
            hwXQoSPortQueueStatisticsDiscardPacketsRate
                Counter64,
            hwXQoSPortQueueStatisticsDiscardBytesRate
                Counter64,
            hwXQoSPortQueueStatisticsDropTailDiscardPacketsRate
                Counter64,
            hwXQoSPortQueueStatisticsDropTailDiscardBytesRate
                Counter64,
            hwXQoSPortQueueStatisticsWredDiscardPacketsRate
                Counter64,
            hwXQoSPortQueueStatisticsWredDiscardBytesRate
                Counter64,
            hwXQoSPortQueueStatisticsTrafficTowardThisPort
                Counter64,
            hwXQoSPortQueueStatisticsPhysicalBandwidthOfPortQoS
                Counter64,
            hwXQoSPortQueueStatisticsQueuePercentage
                Integer32,
            hwXQoSPortQueueStatisticsTotalPackets
                Counter64,
            hwXQoSPortQueueStatisticsTotalBytes
                Counter64
            }

    hwXQoSPortQueueStatisticsInterfaceIndex  OBJECT-TYPE
        SYNTAX   InterfaceIndex
        MAX-ACCESS read-only
        STATUS current
        DESCRIPTION
            " This object indicates the interface index. "
        ::= { hwXQoSPortQueueStatisticsEntry 1 }

    hwXQoSPortQueueStatisticsDirection  OBJECT-TYPE
        SYNTAX INTEGER
            {
            inbound(1),
            outbound(2)
            }
        MAX-ACCESS read-only
        STATUS current
        DESCRIPTION
            " This object indicates the traffic direction whose statistics are queried.
              The value can be one of the following:
              inbound(1)
              outbound(2)."
        ::= { hwXQoSPortQueueStatisticsEntry 2 }

    hwXQoSPortQueueStatisticsQueueIndex  OBJECT-TYPE
        SYNTAX INTEGER
            {
            be(1),
            af1(2),
            af2(3),
            af3(4),
            af4(5),
            ef(6),
            cs6(7),
            cs7(8),
            total(9)
            }
        MAX-ACCESS read-only
        STATUS current
        DESCRIPTION
            " This object indicates the priority of a class queue where statistics are queried.
            The value can be:
            1 be
            2 af1
            3 af2
            4 af3
            5 af4
            6 ef
            7 cs6
            8 cs7
            9 total
            "
        ::= { hwXQoSPortQueueStatisticsEntry 3 }

    hwXQoSPortQueueStatisticsReset  OBJECT-TYPE
        SYNTAX INTEGER
        {
            reset(1)
        }
        MAX-ACCESS read-create
        STATUS current
        DESCRIPTION
            " This object indicates the flag of clearing the statistics.  "
        ::= { hwXQoSPortQueueStatisticsEntry 4 }

    hwXQoSPortQueueStatisticsTotalPassPackets OBJECT-TYPE
        SYNTAX  Counter64
        MAX-ACCESS read-only
        STATUS current
        DESCRIPTION
            " This object indicates the number of passed packets. "
        ::= { hwXQoSPortQueueStatisticsEntry 5 }

    hwXQoSPortQueueStatisticsTotalPassBytes OBJECT-TYPE
        SYNTAX  Counter64
        MAX-ACCESS read-only
        STATUS current
        DESCRIPTION
            " This object indicates the number of forwarded bytes. "
        ::= { hwXQoSPortQueueStatisticsEntry 6 }

    hwXQoSPortQueueStatisticsTotalDiscardPackets OBJECT-TYPE
        SYNTAX  Counter64
        MAX-ACCESS read-only
        STATUS current
        DESCRIPTION
            " This object indicates the number of discarded packets. "
        ::= { hwXQoSPortQueueStatisticsEntry 7 }

    hwXQoSPortQueueStatisticsTotalDiscardBytes OBJECT-TYPE
        SYNTAX  Counter64
        MAX-ACCESS read-only
        STATUS current
        DESCRIPTION
            " This object indicates the number of dropped bytes. "
        ::= { hwXQoSPortQueueStatisticsEntry 8 }

    hwXQoSPortQueueStatisticsDropTailDiscardPackets OBJECT-TYPE
        SYNTAX  Counter64
        MAX-ACCESS read-only
        STATUS current
        DESCRIPTION
            " The value of this object identifies the number of discarded tail packets. "
        ::= { hwXQoSPortQueueStatisticsEntry 9 }

    hwXQoSPortQueueStatisticsDropTailDiscardBytes OBJECT-TYPE
        SYNTAX  Counter64
        MAX-ACCESS read-only
        STATUS current
        DESCRIPTION
            "This object indicates the number of bytes discarded by tail drop. "
        ::= { hwXQoSPortQueueStatisticsEntry 10 }

    hwXQoSPortQueueStatisticsWredDiscardPackets OBJECT-TYPE
        SYNTAX  Counter64
        MAX-ACCESS read-only
        STATUS current
        DESCRIPTION
            " The value of this object identifies the number of packets that are discarded by WRED. "
        ::= { hwXQoSPortQueueStatisticsEntry 11 }

    hwXQoSPortQueueStatisticsWredDiscardBytes OBJECT-TYPE
        SYNTAX  Counter64
        MAX-ACCESS read-only
        STATUS current
        DESCRIPTION
            "This object indicates the number of bytes discarded by WRED. "
        ::= { hwXQoSPortQueueStatisticsEntry 12 }

    hwXQoSPortQueueStatisticsPassPacketsRate OBJECT-TYPE
        SYNTAX  Counter64
        MAX-ACCESS read-only
        STATUS current
        DESCRIPTION
            " This object indicates the packet pass rate. "
        ::= { hwXQoSPortQueueStatisticsEntry 13 }

    hwXQoSPortQueueStatisticsPassBytesRate OBJECT-TYPE
        SYNTAX  Counter64
        MAX-ACCESS read-only
        STATUS current
        DESCRIPTION
            " This object indicates the rate at which bytes are forwarded. "
        ::= { hwXQoSPortQueueStatisticsEntry 14 }

    hwXQoSPortQueueStatisticsDiscardPacketsRate OBJECT-TYPE
        SYNTAX  Counter64
        MAX-ACCESS read-only
        STATUS current
        DESCRIPTION
            " This object indicates the packet drop rate. "
        ::= { hwXQoSPortQueueStatisticsEntry 15 }

    hwXQoSPortQueueStatisticsDiscardBytesRate OBJECT-TYPE
        SYNTAX  Counter64
        MAX-ACCESS read-only
        STATUS current
        DESCRIPTION
            " This object indicates the rate at which bytes are discarded. "
        ::= { hwXQoSPortQueueStatisticsEntry 16 }

    hwXQoSPortQueueStatisticsDropTailDiscardPacketsRate OBJECT-TYPE
        SYNTAX  Counter64
        MAX-ACCESS read-only
        STATUS current
        DESCRIPTION
            " This object indicates the tail packet discarding rate. "
        ::= { hwXQoSPortQueueStatisticsEntry 17 }

    hwXQoSPortQueueStatisticsDropTailDiscardBytesRate OBJECT-TYPE
        SYNTAX  Counter64
        MAX-ACCESS read-only
        STATUS current
        DESCRIPTION
            " This object indicates the rate at which bytes are discarded by tail drop. "
        ::= { hwXQoSPortQueueStatisticsEntry 18 }

    hwXQoSPortQueueStatisticsWredDiscardPacketsRate OBJECT-TYPE
        SYNTAX  Counter64
        MAX-ACCESS read-only
        STATUS current
        DESCRIPTION
            " This object indicates the WRED packet discarding rate."
        ::= { hwXQoSPortQueueStatisticsEntry 19 }

    hwXQoSPortQueueStatisticsWredDiscardBytesRate OBJECT-TYPE
        SYNTAX  Counter64
        MAX-ACCESS read-only
        STATUS current
        DESCRIPTION
            " This object indicates the WRED byte discarding rate."
        ::= { hwXQoSPortQueueStatisticsEntry 20 }

    hwXQoSPortQueueStatisticsTrafficTowardThisPort OBJECT-TYPE
        SYNTAX  Counter64
        UNITS "bps"
        MAX-ACCESS read-only
        STATUS current
        DESCRIPTION
            " This object indicates the port traffic information."
        ::= { hwXQoSPortQueueStatisticsEntry 21 }

    hwXQoSPortQueueStatisticsPhysicalBandwidthOfPortQoS OBJECT-TYPE
        SYNTAX  Counter64
        UNITS "bps"
        MAX-ACCESS read-only
        STATUS current
        DESCRIPTION
            " This object indicates the physical bandwidth of a QoS interface."
        ::= { hwXQoSPortQueueStatisticsEntry 22 }

    hwXQoSPortQueueStatisticsQueuePercentage OBJECT-TYPE
        SYNTAX Integer32 (0..100)
        MAX-ACCESS read-only
        STATUS current
        DESCRIPTION
            "This object indicates the percentage of the queue usage."
        ::= { hwXQoSPortQueueStatisticsEntry 23 }

    hwXQoSPortQueueStatisticsTotalPackets OBJECT-TYPE
        SYNTAX  Counter64
        MAX-ACCESS read-only
        STATUS current
        DESCRIPTION
        " This object indicates the total number of packets."
        ::= { hwXQoSPortQueueStatisticsEntry 24 }

    hwXQoSPortQueueStatisticsTotalBytes OBJECT-TYPE
        SYNTAX  Counter64
        MAX-ACCESS read-only
        STATUS current
        DESCRIPTION
            " This object indicates the total number of bytes."
        ::= { hwXQoSPortQueueStatisticsEntry 25 }

    hwXQoSMulBa8021pPhbCfgInfoTable OBJECT-TYPE
        SYNTAX SEQUENCE OF HwXQoSMulBa8021pPhbCfgInfoEntry
        MAX-ACCESS not-accessible
        STATUS current
        DESCRIPTION
            "Description."
        ::= { hwXQoSBaObjects 32 }

    hwXQoSMulBa8021pPhbCfgInfoEntry OBJECT-TYPE
        SYNTAX HwXQoSMulBa8021pPhbCfgInfoEntry
        MAX-ACCESS not-accessible
        STATUS current
        DESCRIPTION
            "Description."
        INDEX { hwXQoSMulBa8021pPhbIndex, hwXQoSMulBa8021pPri }
        ::= { hwXQoSMulBa8021pPhbCfgInfoTable 1 }

    HwXQoSMulBa8021pPhbCfgInfoEntry ::=
        SEQUENCE {
            hwXQoSMulBa8021pPhbIndex
                Integer32,
            hwXQoSMulBa8021pPri
                Integer32,
            hwXQoSMulBa8021pPhbCos
                INTEGER,
            hwXQoSMulBa8021pPhbRowStatus
                RowStatus
            }

    hwXQoSMulBa8021pPhbIndex OBJECT-TYPE
        SYNTAX Integer32
        MAX-ACCESS read-only
        STATUS current
        DESCRIPTION
            "Description."
        ::= { hwXQoSMulBa8021pPhbCfgInfoEntry 1 }

    hwXQoSMulBa8021pPri OBJECT-TYPE
        SYNTAX Integer32 (0..7)
        MAX-ACCESS read-only
        STATUS current
        DESCRIPTION
            "Description."
        ::= { hwXQoSMulBa8021pPhbCfgInfoEntry 2 }

    hwXQoSMulBa8021pPhbCos OBJECT-TYPE
        SYNTAX INTEGER
            {
            be(1),
            af1(2),
            af2(3),
            af3(4),
            af4(5),
            ef(6),
            cs6(7),
            cs7(8)
            }
        MAX-ACCESS read-write
        STATUS current
        DESCRIPTION
            "Description."
        ::= { hwXQoSMulBa8021pPhbCfgInfoEntry 3 }

    hwXQoSMulBa8021pPhbRowStatus OBJECT-TYPE
        SYNTAX RowStatus
        MAX-ACCESS read-create
        STATUS current
        DESCRIPTION
            "Description."
        ::= { hwXQoSMulBa8021pPhbCfgInfoEntry 50 }

    hwXQoSMulDscpPhbCfgInfoTable OBJECT-TYPE
        SYNTAX SEQUENCE OF HwXQoSMulDscpPhbCfgInfoEntry
        MAX-ACCESS not-accessible
        STATUS current
        DESCRIPTION
            "Description."
        ::= { hwXQoSBaObjects 33 }

    hwXQoSMulDscpPhbCfgInfoEntry OBJECT-TYPE
        SYNTAX HwXQoSMulDscpPhbCfgInfoEntry
        MAX-ACCESS not-accessible
        STATUS current
        DESCRIPTION
            "Description."
        INDEX { hwXQoSMulBaDscpPhbIndex, hwXQoSMulBaDscpPri }
        ::= { hwXQoSMulDscpPhbCfgInfoTable 1 }

    HwXQoSMulDscpPhbCfgInfoEntry ::=
        SEQUENCE {
            hwXQoSMulBaDscpPhbIndex
                Integer32,
            hwXQoSMulBaDscpPri
                Integer32,
            hwXQoSMulBaDscpPhbCos
                INTEGER,
            hwXQoSMulBaDscpPhbRowStatus
                RowStatus
            }

    hwXQoSMulBaDscpPhbIndex OBJECT-TYPE
        SYNTAX Integer32
        MAX-ACCESS read-only
        STATUS current
        DESCRIPTION
            "Description."
        ::= { hwXQoSMulDscpPhbCfgInfoEntry 1 }

    hwXQoSMulBaDscpPri OBJECT-TYPE
        SYNTAX Integer32 (0..63)
        MAX-ACCESS read-only
        STATUS current
        DESCRIPTION
            "Description."
        ::= { hwXQoSMulDscpPhbCfgInfoEntry 2 }

    hwXQoSMulBaDscpPhbCos OBJECT-TYPE
        SYNTAX INTEGER
            {
            be(1),
            af1(2),
            af2(3),
            af3(4),
            af4(5),
            ef(6),
            cs6(7),
            cs7(8)
            }
        MAX-ACCESS read-write
        STATUS current
        DESCRIPTION
            "Description."
        ::= { hwXQoSMulDscpPhbCfgInfoEntry 3 }

    hwXQoSMulBaDscpPhbRowStatus OBJECT-TYPE
        SYNTAX RowStatus
        MAX-ACCESS read-create
        STATUS current
        DESCRIPTION
            "Description."
        ::= { hwXQoSMulDscpPhbCfgInfoEntry 50 }

    hwXQoSBaUserPriPhbCfgInfoTable OBJECT-TYPE
        SYNTAX SEQUENCE OF HwXQoSBaUserPriPhbCfgInfoEntry
        MAX-ACCESS not-accessible
        STATUS current
        DESCRIPTION
            "Description."
        ::= { hwXQoSBaObjects 34 }

    hwXQoSBaUserPriPhbCfgInfoEntry OBJECT-TYPE
        SYNTAX HwXQoSBaUserPriPhbCfgInfoEntry
        MAX-ACCESS not-accessible
        STATUS current
        DESCRIPTION
            "Description."
        INDEX { hwXQoSDSUserPriIndex, hwXQoSUserPriPhbPri }
        ::= { hwXQoSBaUserPriPhbCfgInfoTable 1 }

    HwXQoSBaUserPriPhbCfgInfoEntry ::=
        SEQUENCE {
            hwXQoSDSUserPriIndex
                Integer32,
            hwXQoSUserPriPhbPri
                Integer32,
            hwXQoSUserPriPhbCos
                INTEGER,
            hwXQoSUserPriPhbColour
                INTEGER,
            hwXQoSUserPriPhbRowStatus
                RowStatus
            }

    hwXQoSDSUserPriIndex OBJECT-TYPE
        SYNTAX Integer32
        MAX-ACCESS read-only
        STATUS current
        DESCRIPTION
            "Description."
        ::= { hwXQoSBaUserPriPhbCfgInfoEntry 1 }

    hwXQoSUserPriPhbPri OBJECT-TYPE
        SYNTAX Integer32 (0..7)
        MAX-ACCESS read-only
        STATUS current
        DESCRIPTION
            "Description."
        ::= { hwXQoSBaUserPriPhbCfgInfoEntry 2 }

    hwXQoSUserPriPhbCos OBJECT-TYPE
        SYNTAX INTEGER
            {
            be(1),
            af1(2),
            af2(3),
            af3(4),
            af4(5),
            ef(6),
            cs6(7),
            cs7(8)
            }
        MAX-ACCESS read-write
        STATUS current
        DESCRIPTION
            "Description."
        ::= { hwXQoSBaUserPriPhbCfgInfoEntry 3 }

    hwXQoSUserPriPhbColour OBJECT-TYPE
        SYNTAX INTEGER
            {
            green(1),
            yellow(2),
            red(3)
            }
        MAX-ACCESS read-write
        STATUS current
        DESCRIPTION
            "Description."
        ::= { hwXQoSBaUserPriPhbCfgInfoEntry 4 }

    hwXQoSUserPriPhbRowStatus OBJECT-TYPE
        SYNTAX RowStatus
        MAX-ACCESS read-create
        STATUS current
        DESCRIPTION
            "Description."
        ::= { hwXQoSBaUserPriPhbCfgInfoEntry 50 }

    hwXQoSAAATrustCfgInfoTable OBJECT-TYPE
        SYNTAX SEQUENCE OF HwXQoSAAATrustCfgInfoEntry
        MAX-ACCESS not-accessible
        STATUS current
        DESCRIPTION
            "Description."
        ::= { hwXQoSBaObjects 35 }

    hwXQoSAAATrustCfgInfoEntry OBJECT-TYPE
        SYNTAX HwXQoSAAATrustCfgInfoEntry
        MAX-ACCESS not-accessible
        STATUS current
        DESCRIPTION
            "Description."
        INDEX { hwXQoSAaaDomainName }
        ::= { hwXQoSAAATrustCfgInfoTable 1 }

    HwXQoSAAATrustCfgInfoEntry ::=
        SEQUENCE {
            hwXQoSAaaDomainName
                OCTET STRING,
            hwXQoSAAADsDomainName
                OCTET STRING,
            hwXQoSAAADsRowStatus
                RowStatus
            }

    hwXQoSAaaDomainName OBJECT-TYPE
        SYNTAX OCTET STRING (SIZE (1..31))
        MAX-ACCESS read-only
        STATUS current
        DESCRIPTION
            "Description."
        ::= { hwXQoSAAATrustCfgInfoEntry 1 }

    hwXQoSAAADsDomainName OBJECT-TYPE
        SYNTAX OCTET STRING (SIZE (1..8))
        MAX-ACCESS read-write
        STATUS current
        DESCRIPTION
            "Description."
        ::= { hwXQoSAAATrustCfgInfoEntry 2 }

    hwXQoSAAADsRowStatus OBJECT-TYPE
        SYNTAX RowStatus
        MAX-ACCESS read-create
        STATUS current
        DESCRIPTION
            "Description."
        ::= { hwXQoSAAATrustCfgInfoEntry 50 }

    hwXQoSAAATrust8021pInfoTable OBJECT-TYPE
        SYNTAX SEQUENCE OF HwXQoSAAATrust8021pInfoEntry
        MAX-ACCESS not-accessible
        STATUS current
        DESCRIPTION
            "Description."
        ::= { hwXQoSBaObjects 36 }

    hwXQoSAAATrust8021pInfoEntry OBJECT-TYPE
        SYNTAX HwXQoSAAATrust8021pInfoEntry
        MAX-ACCESS not-accessible
        STATUS current
        DESCRIPTION
            "Description."
        INDEX { hwXQoSAaaDomainName }
        ::= { hwXQoSAAATrust8021pInfoTable 1 }

    HwXQoSAAATrust8021pInfoEntry ::=
        SEQUENCE {
            hwXQoSAAADs8021P
                INTEGER,
            hwXQoSAAADs8021pRowStatus
                RowStatus
            }

    hwXQoSAAADs8021P OBJECT-TYPE
        SYNTAX INTEGER
            {
            disable(1),
            enable(2)
            }
        MAX-ACCESS read-write
        STATUS current
        DESCRIPTION
            "Description."
        ::= { hwXQoSAAATrust8021pInfoEntry 1 }

    hwXQoSAAADs8021pRowStatus OBJECT-TYPE
        SYNTAX RowStatus
        MAX-ACCESS read-create
        STATUS current
        DESCRIPTION
            "Description."
        ::= { hwXQoSAAATrust8021pInfoEntry 50 }

--   Interface view command
    hwXQoSIfActionObjects OBJECT IDENTIFIER ::= { hwXQoSObjects 2 }

--    CAR
    hwXQoSIfCarCfgInfoTable OBJECT-TYPE
        SYNTAX SEQUENCE OF HwXQoSIfCarCfgInfoEntry
        MAX-ACCESS not-accessible
        STATUS current
        DESCRIPTION
            "This table displays information about the committed access rate (CAR) configuration on the interface. The configuration limits the traffic rate on the interface."
        ::= { hwXQoSIfActionObjects 1 }


    hwXQoSIfCarCfgInfoEntry OBJECT-TYPE
        SYNTAX HwXQoSIfCarCfgInfoEntry
        MAX-ACCESS not-accessible
        STATUS current
        DESCRIPTION
            "CAR Configuration Information Entry."
        INDEX { hwXQoSIfCarCfgIfIndex, hwXQoSIfCarVlanID, hwXQoSIfCarDirection }
        ::= { hwXQoSIfCarCfgInfoTable 1 }


    HwXQoSIfCarCfgInfoEntry ::=
        SEQUENCE {
            hwXQoSIfCarCfgIfIndex
                Integer32,
            hwXQoSIfCarVlanID
                Integer32,
            hwXQoSIfCarDirection
                DirectionType,
            hwXQoSIfCarCir
                Integer32,
            hwXQoSIfCarCbs
                Integer32,
            hwXQoSIfCarEbs
                Integer32,
            hwXQoSIfCarPir
                Integer32,
            hwXQoSIfCarPbs
                Integer32,
            hwXQoSIfCarGreenAction
                CarAction,
            hwXQoSIfCarGreenRemarkValue
                Integer32,
            hwXQoSIfCarYellowAction
                CarAction,
            hwXQoSIfCarYellowRemarkValue
                Integer32,
            hwXQoSIfCarRedAction
                CarAction,
            hwXQoSIfCarRedRemarkValue
                Integer32,
            hwXQoSIfCarRowStatus
                RowStatus,
            hwXQoSIfCarCirEx
                Unsigned32,
            hwXQoSIfCarCbsEx
                Unsigned32,
            hwXQoSIfCarPirEx
                Unsigned32,
            hwXQoSIfCarPbsEx
                Unsigned32
         }

    hwXQoSIfCarCfgIfIndex OBJECT-TYPE
        SYNTAX Integer32
        MAX-ACCESS read-only
        STATUS current
        DESCRIPTION
            "This object indicates the interface index."
        ::= { hwXQoSIfCarCfgInfoEntry 1 }

    hwXQoSIfCarVlanID OBJECT-TYPE
        SYNTAX Integer32 (0 | 1..4095)
        MAX-ACCESS read-only
        STATUS current
        DESCRIPTION
            "Vlan ID.
            -1 can't be set.
            0 is the default value"
        ::= { hwXQoSIfCarCfgInfoEntry 2 }

    hwXQoSIfCarDirection OBJECT-TYPE
        SYNTAX DirectionType
        MAX-ACCESS read-only
        STATUS current
        DESCRIPTION
            "This object indicates the upstream and downstream traffic on an interface."
        ::= { hwXQoSIfCarCfgInfoEntry 3 }

    hwXQoSIfCarCir OBJECT-TYPE
        SYNTAX Integer32
        MAX-ACCESS read-create
        STATUS current
        DESCRIPTION
            "Committed Information Rate. Unit: kbps.
            software QoS: 8..155000
            hardware QoS: 100..10000000"
        ::= { hwXQoSIfCarCfgInfoEntry 4 }

    hwXQoSIfCarCbs OBJECT-TYPE
        SYNTAX Integer32
        MAX-ACCESS read-create
        STATUS current
        DESCRIPTION
            "Committed Burst Size. Unit: byte
            software QoS: 1875..19375000
            hardware QoS: 64..33554432"
        ::= { hwXQoSIfCarCfgInfoEntry 5 }

    hwXQoSIfCarEbs OBJECT-TYPE
        SYNTAX Integer32
        MAX-ACCESS read-create
        STATUS current
        DESCRIPTION
            "Excess Burst Size. Unit: byte. 0..19375000
            Only software QoS support this node.
            -1 is returned only when getting value from hardware QoS.
            -1 can't be set."
        DEFVAL { 0 }
        ::= { hwXQoSIfCarCfgInfoEntry 6 }

    hwXQoSIfCarPir OBJECT-TYPE
        SYNTAX Integer32
        MAX-ACCESS read-create
        STATUS current
        DESCRIPTION
            "Peak Information Rate. Unit: kbps. 100..10000000
            Only hardware QoS support this node.
            -1 is returned only when getting value from software QoS.
            -1 can't be set.
            0 is the default value"
        ::= { hwXQoSIfCarCfgInfoEntry 7 }

    hwXQoSIfCarPbs OBJECT-TYPE
        SYNTAX Integer32
        MAX-ACCESS read-create
        STATUS current
        DESCRIPTION
            "Peak Burst Size. Unit: byte.
            64..33554432.
            Only hardware QoS support this node.
            -1 is returned only when getting value from software QoS.
            -1 can't be set.
            0 is the default value"
        ::= { hwXQoSIfCarCfgInfoEntry 8 }

    hwXQoSIfCarGreenAction OBJECT-TYPE
        SYNTAX CarAction
        MAX-ACCESS read-create
        STATUS current
        DESCRIPTION
            "Green Action:
            pass (1)
            discard (2)
            remark IP Precedence (3)
            remark DSCP (4)
            remark MPLS EXP (5)
            remark (6)
            Hardware QoS : pass,discard,remark.
            Software QoS : pass,discard,remark IP Precedence,remark DSCP,remark MPLS EXP.
            "
        DEFVAL { pass }
        ::= { hwXQoSIfCarCfgInfoEntry 9 }

    hwXQoSIfCarGreenRemarkValue OBJECT-TYPE
        SYNTAX Integer32 (-1 | 0..63)
        MAX-ACCESS read-create
        STATUS current
        DESCRIPTION
            "The value is to remark When green action is remarking.
            For remarking DSCP, the range is 0~63;
            For remarking IP Precedence and MPLS EXP, the range is 0~7;
            Only software QoS support this node.
            -1 is returned only when getting value from hardware QoS or when action being pass,discard of software QoS.
            -1 can't be set."
        ::= { hwXQoSIfCarCfgInfoEntry 10 }

    hwXQoSIfCarYellowAction OBJECT-TYPE
        SYNTAX CarAction
        MAX-ACCESS read-create
        STATUS current
        DESCRIPTION
            "Action for yellow packets:
             Unavailable (-1),
             pass (1),
             discard (2),
             mark IP priority (3),
             mark DSCP (4),
             mark MPLS EXP (5),
             and mark (6).
             Only the hardware service quality supports this object, and the hardware service quality supports pass, discard, and mark."
        ::= { hwXQoSIfCarCfgInfoEntry 11 }

    hwXQoSIfCarYellowRemarkValue OBJECT-TYPE
        SYNTAX Integer32 (-1 | 0..63)
        MAX-ACCESS read-create
        STATUS current
        DESCRIPTION
            "The value is to remark When yellow action is remarking.
            For remarking DSCP, the range is 0~63;
            For remarking IP Precedence and MPLS EXP, the range is 0~7;
            Only software QoS support this node.
            -1 is returned only when getting value from hardware QoS or when action being pass,discard of software QoS.
            -1 can't be set."
        ::= { hwXQoSIfCarCfgInfoEntry 12 }

    hwXQoSIfCarRedAction OBJECT-TYPE
        SYNTAX CarAction
        MAX-ACCESS read-create
        STATUS current
        DESCRIPTION
            "Action for red packets:
            pass (1),
            discard (2),
            mark IP priority (3),
            mark DSCP (4),
            mark MPLS EXP (5),
            and mark (6).
            Hardware service quality: pass, discard, and mark. Software service quality: pass, discard, mark IP priority, mark DSCP, and mark MPLS EXP.
            "
        DEFVAL { discard }
        ::= { hwXQoSIfCarCfgInfoEntry 13 }

    hwXQoSIfCarRedRemarkValue OBJECT-TYPE
        SYNTAX Integer32 (-1 | 0..63)
        MAX-ACCESS read-create
        STATUS current
        DESCRIPTION
            "The value is to remark When red action is remarking.
            For remarking DSCP, the range is 0~63;
            For remarking IP Precedence and MPLS EXP, the range is 0~7;
            Only software QoS support this node.
            -1 is returned only when getting value from hardware QoS or when action being pass,discard of software QoS.
            -1 can't be set."
        ::= { hwXQoSIfCarCfgInfoEntry 14 }

    hwXQoSIfCarRowStatus OBJECT-TYPE
        SYNTAX RowStatus
        MAX-ACCESS read-create
        STATUS current
        DESCRIPTION
            "RowStatus. Three actions are used: active,
            createAndGo, destroy"
        ::= { hwXQoSIfCarCfgInfoEntry 15 }

    hwXQoSIfCarCirEx OBJECT-TYPE
        SYNTAX Unsigned32
        MAX-ACCESS read-create
        STATUS current
        DESCRIPTION
            "This object indicates the CIR."
        ::= { hwXQoSIfCarCfgInfoEntry 16 }

    hwXQoSIfCarCbsEx OBJECT-TYPE
        SYNTAX Unsigned32
        MAX-ACCESS read-create
        STATUS current
        DESCRIPTION
            "Committed Burst Size. Unit: byte."
        ::= { hwXQoSIfCarCfgInfoEntry 17 }

    hwXQoSIfCarPirEx OBJECT-TYPE
        SYNTAX Unsigned32
        MAX-ACCESS read-create
        STATUS current
        DESCRIPTION
            "This object indicates the PIR."
        ::= { hwXQoSIfCarCfgInfoEntry 18 }

    hwXQoSIfCarPbsEx OBJECT-TYPE
        SYNTAX Unsigned32
        MAX-ACCESS read-create
        STATUS current
        DESCRIPTION
            "Peak Burst Size. Unit: byte."
        ::= { hwXQoSIfCarCfgInfoEntry 19 }

--    mirror behavior
    hwXQoSIfMirrorCfgInfoTable OBJECT-TYPE
        SYNTAX SEQUENCE OF HwXQoSIfMirrorCfgInfoEntry
        MAX-ACCESS not-accessible
        STATUS current
        DESCRIPTION
            "A table of Mirror configuration information."
        ::= { hwXQoSIfActionObjects 2 }

    hwXQoSIfMirrorCfgInfoEntry OBJECT-TYPE
        SYNTAX HwXQoSIfMirrorCfgInfoEntry
        MAX-ACCESS not-accessible
        STATUS current
        DESCRIPTION
            "Mirror Configuration Information Entry."
        INDEX { hwXQoSIfMirrorCfgIfIndex, hwXQoSIfMirrorCfgVlanID, hwXQoSIfMirrorDirection }
        ::= { hwXQoSIfMirrorCfgInfoTable 1 }

    HwXQoSIfMirrorCfgInfoEntry ::=
        SEQUENCE {
            hwXQoSIfMirrorCfgIfIndex
                Integer32,
            hwXQoSIfMirrorCfgVlanID
                Integer32,
            hwXQoSIfMirrorDirection
                DirectionType,
            hwXQoSIfMirrorObserveIndex
                Integer32,
            hwXQoSIfMirrorRowStatus
                RowStatus
         }

    hwXQoSIfMirrorCfgIfIndex OBJECT-TYPE
        SYNTAX Integer32
        MAX-ACCESS read-only
        STATUS current
        DESCRIPTION
            "Interface Index, equal to ifIndex."
        ::= { hwXQoSIfMirrorCfgInfoEntry 1 }

    hwXQoSIfMirrorCfgVlanID OBJECT-TYPE
        SYNTAX Integer32 (0 | 1..4095)
        MAX-ACCESS read-only
        STATUS current
        DESCRIPTION
            "Vlan ID.
            -1 can't be set.
            0 is the default value"
        ::= { hwXQoSIfMirrorCfgInfoEntry 2 }

    hwXQoSIfMirrorDirection OBJECT-TYPE
        SYNTAX DirectionType
        MAX-ACCESS read-only
        STATUS current
        DESCRIPTION
            "Policy direction:
            inbound (1)
            outbound (2)"
        ::= { hwXQoSIfMirrorCfgInfoEntry 3 }

    hwXQoSIfMirrorObserveIndex OBJECT-TYPE
        SYNTAX Integer32 (1..16)
        MAX-ACCESS read-create
        STATUS current
        DESCRIPTION
            "The mirror observe port number"
        ::= { hwXQoSIfMirrorCfgInfoEntry 4 }

    hwXQoSIfMirrorRowStatus OBJECT-TYPE
        SYNTAX RowStatus
        MAX-ACCESS read-create
        STATUS current
        DESCRIPTION
            "RowStatus. Three actions are used: active,
            createAndGo, destroy"
        ::= { hwXQoSIfMirrorCfgInfoEntry 5 }

--    Urpf behavior
    hwXQoSIfUrpfCfgInfoTable OBJECT-TYPE
        SYNTAX SEQUENCE OF HwXQoSIfUrpfCfgInfoEntry
        MAX-ACCESS not-accessible
        STATUS current
        DESCRIPTION
            "A table of Urpf configuration information."
        ::= { hwXQoSIfActionObjects 3 }

    hwXQoSIfUrpfCfgInfoEntry OBJECT-TYPE
        SYNTAX HwXQoSIfUrpfCfgInfoEntry
        MAX-ACCESS not-accessible
        STATUS current
        DESCRIPTION
            "Urpf Configuration Information Entry."
        INDEX { hwXQoSIfUrpfCfgIfIndex, hwXQoSIfUrpfCfgVlanID }
        ::= { hwXQoSIfUrpfCfgInfoTable 1 }

    HwXQoSIfUrpfCfgInfoEntry ::=
        SEQUENCE {
            hwXQoSIfUrpfCfgIfIndex
                Integer32,
            hwXQoSIfUrpfCfgVlanID
                Integer32,
            hwXQoSIfUrpfCtrlType
                UrpfCtrlType,
            hwXQoSIfUrpfAllowDefault
                INTEGER,
            hwXQoSIfUrpfRowStatus
                RowStatus
         }

    hwXQoSIfUrpfCfgIfIndex OBJECT-TYPE
        SYNTAX Integer32
        MAX-ACCESS read-only
        STATUS current
        DESCRIPTION
            "The value of this object identifies the interface index.The object has no default value."
        ::= { hwXQoSIfUrpfCfgInfoEntry 1 }

    hwXQoSIfUrpfCfgVlanID OBJECT-TYPE
        SYNTAX Integer32 (0 | 1..4095)
        MAX-ACCESS read-only
        STATUS current
        DESCRIPTION
            "Vlan ID.
            -1 can't be set.
            0 is the default value"
        ::= { hwXQoSIfUrpfCfgInfoEntry 2 }

    hwXQoSIfUrpfCtrlType OBJECT-TYPE
        SYNTAX UrpfCtrlType
        MAX-ACCESS read-create
        STATUS current
        DESCRIPTION
            "The value of this object identifies the control type of URPF.The value can be either of the following:Strict(1)
,Loose(2).The object has no default value."
        ::= { hwXQoSIfUrpfCfgInfoEntry 3 }

    hwXQoSIfUrpfAllowDefault OBJECT-TYPE
        SYNTAX INTEGER
            {
            false(0),
            true(1)
            }
        MAX-ACCESS read-create
        STATUS current
        DESCRIPTION
            "The value of this object identifies whether the default route is allowed according to URPF.The value can be either of the following:
            0: indicates that the default route is not allowed.
            1: indicates that the default route is allowed.
            The object has no default value."
        ::= { hwXQoSIfUrpfCfgInfoEntry 4 }

    hwXQoSIfUrpfRowStatus OBJECT-TYPE
        SYNTAX RowStatus
        MAX-ACCESS read-create
        STATUS current
        DESCRIPTION
            "This value of this object identifies the row status.The value can be any of the following:Active(1),CreateAndGo(4),Destroy(6).The object has no default value."
        ::= { hwXQoSIfUrpfCfgInfoEntry 5 }

--    Sampling behavior
    hwXQoSIfSamplingCfgInfoTable OBJECT-TYPE
        SYNTAX SEQUENCE OF HwXQoSIfSamplingCfgInfoEntry
        MAX-ACCESS not-accessible
        STATUS current
        DESCRIPTION
            "A table of Sampling configuration information."
        ::= { hwXQoSIfActionObjects 4 }

    hwXQoSIfSamplingCfgInfoEntry OBJECT-TYPE
        SYNTAX HwXQoSIfSamplingCfgInfoEntry
        MAX-ACCESS not-accessible
        STATUS current
        DESCRIPTION
            "Sampling Configuration Information Entry."
        INDEX { hwXQoSIfSamplingIfIndex, hwXQoSIfSamplingVlanID, hwXQoSIfSamplingDirection }
        ::= { hwXQoSIfSamplingCfgInfoTable 1 }

    HwXQoSIfSamplingCfgInfoEntry ::=
        SEQUENCE {
            hwXQoSIfSamplingIfIndex
                Integer32,
            hwXQoSIfSamplingVlanID
                Integer32,
            hwXQoSIfSamplingDirection
                DirectionType,
            hwXQoSIfSamplingType
                SampleType,
            hwXQoSIfSamplingNum
                Integer32,
            hwXQoSIfSamplingRowStatus
                RowStatus
         }

    hwXQoSIfSamplingIfIndex OBJECT-TYPE
        SYNTAX Integer32
        MAX-ACCESS read-only
        STATUS current
        DESCRIPTION
            "Indicates the index of a sampling interface."
        ::= { hwXQoSIfSamplingCfgInfoEntry 1 }

    hwXQoSIfSamplingVlanID OBJECT-TYPE
        SYNTAX Integer32 (0 | 1..4095)
        MAX-ACCESS read-only
        STATUS current
        DESCRIPTION
            "Indicates the VLAN ID of a sampling interface."
        ::= { hwXQoSIfSamplingCfgInfoEntry 2 }

    hwXQoSIfSamplingDirection OBJECT-TYPE
        SYNTAX DirectionType
        MAX-ACCESS read-only
        STATUS current
        DESCRIPTION
            "Indicates whether the interface is an inbound interface or an outbound interface.
            inbound (1)
            outbound (2)"
        ::= { hwXQoSIfSamplingCfgInfoEntry 3}

    hwXQoSIfSamplingType OBJECT-TYPE
        SYNTAX SampleType
        MAX-ACCESS read-create
        STATUS current
        DESCRIPTION
            "Indicates the sampling type.
            Fix-packets(1)
            Fix-time(2)
            Random-packets(3)
            Random-time(4)
            "
        ::= { hwXQoSIfSamplingCfgInfoEntry 4 }

    hwXQoSIfSamplingNum OBJECT-TYPE
        SYNTAX Integer32 (1..65535)
        MAX-ACCESS read-create
        STATUS current
        DESCRIPTION
            "Indicates the sampling parameter."
        ::= { hwXQoSIfSamplingCfgInfoEntry 5 }

    hwXQoSIfSamplingRowStatus OBJECT-TYPE
        SYNTAX RowStatus
        MAX-ACCESS read-create
        STATUS current
        DESCRIPTION
            "Indicates the row status. Three actions are used: active,
            createAndGo, destroy"
        ::= { hwXQoSIfSamplingCfgInfoEntry 6 }

--    lr
    hwXQoSIfLrCfgInfoTable OBJECT-TYPE
        SYNTAX SEQUENCE OF HwXQoSIfLrCfgInfoEntry
        MAX-ACCESS not-accessible
        STATUS current
        DESCRIPTION
            "This table limits the sending rate on an interface."
        ::= { hwXQoSIfActionObjects 5 }

    hwXQoSIfLrCfgInfoEntry OBJECT-TYPE
        SYNTAX HwXQoSIfLrCfgInfoEntry
        MAX-ACCESS not-accessible
        STATUS current
        DESCRIPTION
            "Lr Configuration Information Entry."
        INDEX { hwXQoSIfLrCfgIfIndex, hwXQoSIfLrCfgVlanID }
        ::= { hwXQoSIfLrCfgInfoTable 1 }

    HwXQoSIfLrCfgInfoEntry ::=
        SEQUENCE {
            hwXQoSIfLrCfgIfIndex
                Integer32,
            hwXQoSIfLrCfgVlanID
                Integer32,
            hwXQoSIfLrCir
                Integer32,
            hwXQoSIfLrRowStatus
                RowStatus,
            hwXQoSIfLrCbs
                Integer32,
            hwXQoSIfInPhyBandwidth
                Integer32,
            hwXQoSIfOutPhyBandwidth
                Integer32,
            hwXQoSIfInActualBandwidth
                OCTET STRING,
            hwXQoSIfOutActualBandwidth
                OCTET STRING,
            hwXQoSIfLrRealCir
                Unsigned32
         }

    hwXQoSIfLrCfgIfIndex OBJECT-TYPE
        SYNTAX Integer32
        MAX-ACCESS read-only
        STATUS current
        DESCRIPTION
            "This object indicates the interface index."
        ::= { hwXQoSIfLrCfgInfoEntry 1 }

    hwXQoSIfLrCfgVlanID OBJECT-TYPE
        SYNTAX Integer32 (0 | 1..4095)
        MAX-ACCESS read-only
        STATUS current
        DESCRIPTION
            "Vlan ID.
            -1 cannot be set.
            0 is the default value"
        ::= { hwXQoSIfLrCfgInfoEntry 2 }

    hwXQoSIfLrCir OBJECT-TYPE
        SYNTAX Integer32
        MAX-ACCESS read-create
        STATUS current
        DESCRIPTION
            "This object indicates the CIR. The value ranges from 1 to the interface bandwidth. "
        ::= { hwXQoSIfLrCfgInfoEntry 3 }

    hwXQoSIfLrRowStatus OBJECT-TYPE
        SYNTAX RowStatus
        MAX-ACCESS read-create
        STATUS current
        DESCRIPTION
            "This value of this object identifies the row status.The value can be any of the following:CreateAndGo(4),
Destroy(6),Active(1).The object has no default value."
        ::= { hwXQoSIfLrCfgInfoEntry 4 }

     hwXQoSIfLrCbs OBJECT-TYPE
        SYNTAX Integer32
        MAX-ACCESS read-create
        STATUS current
        DESCRIPTION
            "This object indicates the CBS."
        ::= { hwXQoSIfLrCfgInfoEntry 5 }

     hwXQoSIfInPhyBandwidth OBJECT-TYPE
        SYNTAX Integer32
        MAX-ACCESS read-only
        STATUS current
        DESCRIPTION
            "The inbound physical bandwidth Unit: bps."
        ::= { hwXQoSIfLrCfgInfoEntry 6 }

       hwXQoSIfOutPhyBandwidth OBJECT-TYPE
        SYNTAX Integer32
        MAX-ACCESS read-only
        STATUS current
        DESCRIPTION
            "The outbound physical bandwidth Unit: bps."
        ::= { hwXQoSIfLrCfgInfoEntry 7 }

      hwXQoSIfInActualBandwidth OBJECT-TYPE
        SYNTAX OCTET STRING (SIZE (1..31))
        MAX-ACCESS read-only
        STATUS current
        DESCRIPTION
            "The inbound actual bandwidth Unit: bps."
        ::= { hwXQoSIfLrCfgInfoEntry 8 }

      hwXQoSIfOutActualBandwidth OBJECT-TYPE
        SYNTAX OCTET STRING (SIZE (1..31))
        MAX-ACCESS read-only
        STATUS current
        DESCRIPTION
            "The outbound actual bandwidth Unit: bps."
        ::= { hwXQoSIfLrCfgInfoEntry 9 }

      hwXQoSIfLrRealCir OBJECT-TYPE
        SYNTAX Unsigned32
        MAX-ACCESS read-only
        STATUS current
        DESCRIPTION
            "This object indicates the CIR value, which ranges from 1 to the interface bandwidth. There is no default value. This object is used to replace the hwXQoSIfLrCir object."
        ::= { hwXQoSIfLrCfgInfoEntry 10 }

--    queue
    hwXQoSIfQueueCfgInfoTable OBJECT-TYPE
        SYNTAX SEQUENCE OF HwXQoSIfQueueCfgInfoEntry
        MAX-ACCESS not-accessible
        STATUS current
        DESCRIPTION
            "This table is used to query port queue configurations."
        ::= { hwXQoSIfActionObjects 6 }

    hwXQoSIfQueueCfgInfoEntry OBJECT-TYPE
        SYNTAX HwXQoSIfQueueCfgInfoEntry
        MAX-ACCESS not-accessible
        STATUS current
        DESCRIPTION
            "Qos queue Configuration Information Entry."
        INDEX { hwXQoSIfQueueCfgIfIndex, hwXQoSIfQueueCfgVlanID, hwXQoSIfQueueDirection, hwXQoSIfQueueCfgCosType }
        ::= { hwXQoSIfQueueCfgInfoTable 1 }

    HwXQoSIfQueueCfgInfoEntry ::=
        SEQUENCE {
            hwXQoSIfQueueCfgIfIndex
                Integer32,
            hwXQoSIfQueueCfgVlanID
                Integer32,
            hwXQoSIfQueueDirection
                INTEGER,
            hwXQoSIfQueueCfgCosType
                INTEGER,
            hwXQoSIfQueuePriority
                INTEGER,
            hwXQoSIfQueueCir
                Unsigned32,
            hwXQoSIfQueuePir
                Unsigned32,
            hwXQoSIfQueueCirPercent
                Integer32,
            hwXQoSIfQueuePirPercent
                Integer32,
            hwXQoSIfQueueWeight
                Integer32,
            hwXQoSIfQueueMode
                INTEGER,
            hwXQoSIfQueueRowStatus
                RowStatus
         }

    hwXQoSIfQueueCfgIfIndex OBJECT-TYPE
        SYNTAX Integer32 (0..2147483647)
        MAX-ACCESS read-only
        STATUS current
        DESCRIPTION
            "This object indicates the interface index."
        ::= { hwXQoSIfQueueCfgInfoEntry 1 }

    hwXQoSIfQueueCfgVlanID OBJECT-TYPE
        SYNTAX Integer32 (0)
        MAX-ACCESS read-only
        STATUS current
        DESCRIPTION
            "Vlan ID.
            0 is the default value"
        ::= { hwXQoSIfQueueCfgInfoEntry 2 }

    hwXQoSIfQueueDirection OBJECT-TYPE
        SYNTAX INTEGER
            {
            outbound(2)
            }
        MAX-ACCESS read-only
        STATUS current
        DESCRIPTION
            "This object indicates the traffic direction in which queue statistics are queried."
        ::= { hwXQoSIfQueueCfgInfoEntry 3 }

    hwXQoSIfQueueCfgCosType OBJECT-TYPE
        SYNTAX INTEGER
            {
            be(1),
            af1(2),
            af2(3),
            af3(4),
            af4(5),
            ef(6),
            cs6(7),
            cs7(8)
            }
        MAX-ACCESS read-only
        STATUS current
        DESCRIPTION
            "The value of this object identifies CoS of the queue.The value ranges from 1 to 8. CS(8),CS(7),EF(6),AF(5),AF(4),AF(3),AF(2),BE(1).The default value is BE(1). "
        ::= { hwXQoSIfQueueCfgInfoEntry 4 }

    hwXQoSIfQueuePriority OBJECT-TYPE
        SYNTAX INTEGER
            {
            pq(1),
            wfq(2),
            lpq(3)
            }
        MAX-ACCESS read-create
        STATUS current
        DESCRIPTION
            "The queue priority of PQ queue mode.
            The value can be any of the following:
                PQ(1)
                WFQ(2)
                LPQ(3)"
        ::= { hwXQoSIfQueueCfgInfoEntry 5 }

    hwXQoSIfQueueCir OBJECT-TYPE
        SYNTAX Unsigned32
        MAX-ACCESS read-create
        STATUS current
        DESCRIPTION
            "The value of this object identifies CIR of the queue.The value ranges from 0 to 10000000.The object has no default value."
        ::= { hwXQoSIfQueueCfgInfoEntry 6 }

    hwXQoSIfQueuePir OBJECT-TYPE
        SYNTAX Unsigned32
        MAX-ACCESS read-create
        STATUS current
        DESCRIPTION
            "This object indicates the PIR. The value ranges from 0 to 10000000. "
        ::= { hwXQoSIfQueueCfgInfoEntry 7 }

    hwXQoSIfQueueCirPercent OBJECT-TYPE
        SYNTAX Integer32
        MAX-ACCESS read-create
        STATUS current
        DESCRIPTION
            "The qos queue cir-percentage."
        ::= { hwXQoSIfQueueCfgInfoEntry 8 }

    hwXQoSIfQueuePirPercent OBJECT-TYPE
        SYNTAX Integer32
        MAX-ACCESS read-create
        STATUS current
        DESCRIPTION
            "This object indicates the proportion of the queue PIR."
        ::= { hwXQoSIfQueueCfgInfoEntry 9 }

     hwXQoSIfQueueWeight OBJECT-TYPE
        SYNTAX Integer32
        MAX-ACCESS read-create
        STATUS current
        DESCRIPTION
            "The queue weight of wrr or drr queue mode"
        ::= { hwXQoSIfQueueCfgInfoEntry 10 }

    hwXQoSIfQueueMode OBJECT-TYPE
        SYNTAX INTEGER {
            pq(1),
            wrr(3),
            wfq(4),
            default(5),
            drr(6)
           }
        MAX-ACCESS read-create
        STATUS current
        DESCRIPTION
            "The value of this object identifies the scheduling mode for queues.The value can be either of the following:
pq(1),wrr(3),wfq(4),default(5).The NE40E can support either of the following value:pq(1),wfq(4).The default value is default(5). "
        ::= { hwXQoSIfQueueCfgInfoEntry 11 }

    hwXQoSIfQueueRowStatus OBJECT-TYPE
        SYNTAX RowStatus
        MAX-ACCESS read-create
        STATUS current
        DESCRIPTION
            "This value of this object identifies the row status. The value can be any of the following: CreateAndGo(4), Destroy(6), Active(1). The object has no default value."
        ::= { hwXQoSIfQueueCfgInfoEntry 12 }

--    observe port
    hwXQoSIfObserveCfgInfoTable OBJECT-TYPE
        SYNTAX SEQUENCE OF HwXQoSIfObserveCfgInfoEntry
        MAX-ACCESS not-accessible
        STATUS current
        DESCRIPTION
            "A table of Observe configuration information."
        ::= { hwXQoSIfActionObjects 7 }

    hwXQoSIfObserveCfgInfoEntry OBJECT-TYPE
        SYNTAX HwXQoSIfObserveCfgInfoEntry
        MAX-ACCESS not-accessible
        STATUS current
        DESCRIPTION
            "Observe Configuration Information Entry."
        INDEX { hwXQoSIfObserveIndex }
        ::= { hwXQoSIfObserveCfgInfoTable 1 }

    HwXQoSIfObserveCfgInfoEntry ::=
        SEQUENCE {
            hwXQoSIfObserveIndex
                Integer32,
            hwXQoSIfObserveIfIndex
                Integer32,
            hwXQoSIfObserveRowStatus
                RowStatus
         }

    hwXQoSIfObserveIndex OBJECT-TYPE
        SYNTAX Integer32
        MAX-ACCESS read-only
        STATUS current
        DESCRIPTION
            "The Observe number "
        ::= { hwXQoSIfObserveCfgInfoEntry 1 }

    hwXQoSIfObserveIfIndex OBJECT-TYPE
        SYNTAX Integer32
        MAX-ACCESS read-create
        STATUS current
        DESCRIPTION
            "Interface Index, equal to ifIndex."
        ::= { hwXQoSIfObserveCfgInfoEntry 2 }

    hwXQoSIfObserveRowStatus OBJECT-TYPE
        SYNTAX RowStatus
        MAX-ACCESS read-create
        STATUS current
        DESCRIPTION
            "RowStatus. Three actions are used: active,
            createAndGo, destroy"
        ::= { hwXQoSIfObserveCfgInfoEntry 3 }

-- Wred
    hwXQoSIfWredCfgInfoTable OBJECT-TYPE
        SYNTAX SEQUENCE OF HwXQoSIfWredCfgInfoEntry
        MAX-ACCESS not-accessible
        STATUS current
        DESCRIPTION
            "A table of Wred configuration information."
        ::= { hwXQoSIfActionObjects 8 }

    hwXQoSIfWredCfgInfoEntry OBJECT-TYPE
        SYNTAX HwXQoSIfWredCfgInfoEntry
        MAX-ACCESS not-accessible
        STATUS current
        DESCRIPTION
            "Wred Configuration Information Entry."
        INDEX { hwXQoSIfWredQueueIndex, hwXQoSIfWredDirection}
        ::= { hwXQoSIfWredCfgInfoTable 1 }

    HwXQoSIfWredCfgInfoEntry ::=
        SEQUENCE {
            hwXQoSIfWredQueueIndex
                Integer32,
            hwXQoSIfWredDirection
                DirectionType,
            hwXQoSIfWredType
                INTEGER,
            hwXQoSIfWredLowlimit
                Integer32,
            hwXQoSIfWredHighlimit
                Integer32,
            hwXQoSIfWredDiscardProbability
                Integer32,
            hwXQoSIfWredHighDiscardProbability
                Integer32,
            hwXQoSIfWredRowStatus
                RowStatus
         }

    hwXQoSIfWredQueueIndex OBJECT-TYPE
        SYNTAX Integer32(0..7)
        MAX-ACCESS read-only
        STATUS current
        DESCRIPTION
            "The Wred queue index "
        ::= { hwXQoSIfWredCfgInfoEntry 1 }

    hwXQoSIfWredDirection OBJECT-TYPE
        SYNTAX DirectionType
        MAX-ACCESS read-only
        STATUS current
        DESCRIPTION
            "Policy direction:
            inbound (1)
            outbound (2)"
        ::= { hwXQoSIfWredCfgInfoEntry 2 }

    hwXQoSIfWredType OBJECT-TYPE
        SYNTAX INTEGER
        {
            ipPrec(1),
            dscp(2)
        }
        MAX-ACCESS read-write
        STATUS current
        DESCRIPTION
            "IP-Prec Based (1)
            DSCP Based (2)"
        DEFVAL { ipPrec }
        ::= { hwXQoSIfWredCfgInfoEntry 3 }

    hwXQoSIfWredLowlimit OBJECT-TYPE
        SYNTAX Integer32
        MAX-ACCESS read-create
        STATUS current
        DESCRIPTION
            "The Wred Lowlimit. unit:packet"
        ::= { hwXQoSIfWredCfgInfoEntry 4 }

     hwXQoSIfWredHighlimit OBJECT-TYPE
        SYNTAX Integer32
        MAX-ACCESS read-create
        STATUS current
        DESCRIPTION
            "The Wred Highlimit.unit:packet"
        ::= { hwXQoSIfWredCfgInfoEntry 5 }

    hwXQoSIfWredDiscardProbability OBJECT-TYPE
        SYNTAX Integer32(1..100)
        MAX-ACCESS read-create
        STATUS current
        DESCRIPTION
            "The Wred Discard Probability."
        ::= { hwXQoSIfWredCfgInfoEntry 6 }

    hwXQoSIfWredHighDiscardProbability OBJECT-TYPE
        SYNTAX Integer32(1..100)
        MAX-ACCESS read-create
        STATUS current
        DESCRIPTION
            "The Wred High Discard Probability."
        ::= { hwXQoSIfWredCfgInfoEntry 7 }

    hwXQoSIfWredRowStatus OBJECT-TYPE
        SYNTAX RowStatus
        MAX-ACCESS read-create
        STATUS current
        DESCRIPTION
            "RowStatus. Three actions are used: active,
            createAndGo, destroy"
        ::= { hwXQoSIfWredCfgInfoEntry 8 }

-- 8021p-local-precedence-map
    hwXQoSIf8021PMapCfgInfoTable OBJECT-TYPE
        SYNTAX SEQUENCE OF HwXQoSIf8021PMapCfgInfoEntry
        MAX-ACCESS not-accessible
        STATUS current
        DESCRIPTION
            "A table of 8021PMap configuration information."
        ::= { hwXQoSIfActionObjects 9 }


    hwXQoSIf8021PMapCfgInfoEntry OBJECT-TYPE
        SYNTAX HwXQoSIf8021PMapCfgInfoEntry
        MAX-ACCESS not-accessible
        STATUS current
        DESCRIPTION
            "8021PMap Configuration Information Entry."
        INDEX { hwXQoSIf8021PMap8021PValue }
        ::= { hwXQoSIf8021PMapCfgInfoTable 1 }

    HwXQoSIf8021PMapCfgInfoEntry ::=
        SEQUENCE {
            hwXQoSIf8021PMap8021PValue
                Integer32,
            hwXQoSIf8021PMapLocalPrecedence
                Integer32,
            hwXQoSIf8021PMapRowStatus
                RowStatus
         }

    hwXQoSIf8021PMap8021PValue OBJECT-TYPE
        SYNTAX Integer32(0..7)
        MAX-ACCESS read-only
        STATUS current
        DESCRIPTION
            "The 8021PMap 802.1p value "
        ::= { hwXQoSIf8021PMapCfgInfoEntry 1 }

    hwXQoSIf8021PMapLocalPrecedence OBJECT-TYPE
        SYNTAX Integer32(0..7)
        MAX-ACCESS read-create
        STATUS current
        DESCRIPTION
            "The 8021PMap Local Precedence."
        ::= { hwXQoSIf8021PMapCfgInfoEntry 2 }

    hwXQoSIf8021PMapRowStatus OBJECT-TYPE
        SYNTAX RowStatus
        MAX-ACCESS read-create
        STATUS current
        DESCRIPTION
            "RowStatus. Three actions are used: active,
            createAndGo, destroy"
        ::= { hwXQoSIf8021PMapCfgInfoEntry 3 }

-- mpls exp-exp-map
    hwXQoSIfMplsExpMapCfgInfoTable OBJECT-TYPE
        SYNTAX SEQUENCE OF HwXQoSIfMplsExpMapCfgInfoEntry
        MAX-ACCESS not-accessible
        STATUS current
        DESCRIPTION
            "A table of mpls exp-exp-map configuration information."
        ::= { hwXQoSIfActionObjects 10 }

    hwXQoSIfMplsExpMapCfgInfoEntry OBJECT-TYPE
        SYNTAX HwXQoSIfMplsExpMapCfgInfoEntry
        MAX-ACCESS not-accessible
        STATUS current
        DESCRIPTION
            "mpls exp-exp-map Configuration Information Entry."
        INDEX { hwXQoSIfMplsExpMapIfIndex, hwXQoSIfMplsExpMapInbound }
        ::= { hwXQoSIfMplsExpMapCfgInfoTable 1 }

    HwXQoSIfMplsExpMapCfgInfoEntry ::=
        SEQUENCE {
            hwXQoSIfMplsExpMapIfIndex
                Integer32,
            hwXQoSIfMplsExpMapInbound
                Integer32,
            hwXQoSIfMplsExpMapOutbound
                Integer32,
            hwXQoSIfMplsExpMapRowStatus
                RowStatus
         }

    hwXQoSIfMplsExpMapIfIndex OBJECT-TYPE
        SYNTAX Integer32
        MAX-ACCESS read-only
        STATUS current
        DESCRIPTION
            "Interface Index, equal to ifIndex."
        ::= { hwXQoSIfMplsExpMapCfgInfoEntry 1 }

    hwXQoSIfMplsExpMapInbound OBJECT-TYPE
        SYNTAX Integer32(0..7)
        MAX-ACCESS read-only
        STATUS current
        DESCRIPTION
            "The mpls exp-exp-map inbound value"
        ::= { hwXQoSIfMplsExpMapCfgInfoEntry 2 }

    hwXQoSIfMplsExpMapOutbound OBJECT-TYPE
        SYNTAX Integer32(0..7)
        MAX-ACCESS read-create
        STATUS current
        DESCRIPTION
            "The mpls exp-exp-map outbound value"
        ::= { hwXQoSIfMplsExpMapCfgInfoEntry 3 }

    hwXQoSIfMplsExpMapRowStatus OBJECT-TYPE
        SYNTAX RowStatus
        MAX-ACCESS read-create
        STATUS current
        DESCRIPTION
            "RowStatus. Three actions are used: active,
            createAndGo, destroy"
        ::= { hwXQoSIfMplsExpMapCfgInfoEntry 4 }

--    Default priority
    hwXQoSIfDefaultPriorityCfgInfoTable OBJECT-TYPE
        SYNTAX SEQUENCE OF HwXQoSIfDefaultPriorityCfgInfoEntry
        MAX-ACCESS not-accessible
        STATUS current
        DESCRIPTION
            "A table of default priority configuration information."
        ::= { hwXQoSIfActionObjects 11}

    hwXQoSIfDefaultPriorityCfgInfoEntry OBJECT-TYPE
        SYNTAX HwXQoSIfDefaultPriorityCfgInfoEntry
        MAX-ACCESS not-accessible
        STATUS current
        DESCRIPTION
            "Default priority Configuration Information Entry."
        INDEX { hwXQoSIfDefaultPriorityIfIndex, hwXQoSIfDefaultPriorityVlanID }
        ::= { hwXQoSIfDefaultPriorityCfgInfoTable 1 }

    HwXQoSIfDefaultPriorityCfgInfoEntry ::=
        SEQUENCE {
            hwXQoSIfDefaultPriorityIfIndex
                Integer32,
            hwXQoSIfDefaultPriorityVlanID
                Integer32,
            hwXQoSIfDefaultPriorityValue
                Integer32,
            hwXQoSIfDefaultPriorityRowStatus
                RowStatus
         }

    hwXQoSIfDefaultPriorityIfIndex OBJECT-TYPE
        SYNTAX Integer32
        MAX-ACCESS read-only
        STATUS current
        DESCRIPTION
            "Interface Index, equal to ifIndex."
        ::= { hwXQoSIfDefaultPriorityCfgInfoEntry 1 }

    hwXQoSIfDefaultPriorityVlanID OBJECT-TYPE
        SYNTAX Integer32 (0 | 1..4094)
        MAX-ACCESS read-create
        STATUS current
        DESCRIPTION
            "Vlan ID.
            -1 can't be set.
            0 is the default value"
        ::= { hwXQoSIfDefaultPriorityCfgInfoEntry 2 }

    hwXQoSIfDefaultPriorityValue OBJECT-TYPE
        SYNTAX Integer32 (0..7)
        MAX-ACCESS read-create
        STATUS current
        DESCRIPTION
            "The default priority value "
        ::= { hwXQoSIfDefaultPriorityCfgInfoEntry 3 }

    hwXQoSIfDefaultPriorityRowStatus OBJECT-TYPE
        SYNTAX RowStatus
        MAX-ACCESS read-create
        STATUS current
        DESCRIPTION
            "RowStatus. Three actions are used: active,
            createAndGo, destroy"
    ::= { hwXQoSIfDefaultPriorityCfgInfoEntry 4 }

    -- 1.3.6.1.4.1.2011.5.25.32.4.1.2.12
    hwXQoSIfSoftCarTable OBJECT-TYPE
        SYNTAX SEQUENCE OF HwXQoSIfSoftCarEntry
        MAX-ACCESS not-accessible
        STATUS current
        DESCRIPTION
        "A table of interface software CAR  configuration  information."
        ::= { hwXQoSIfActionObjects 12 }

    -- 1.3.6.1.4.1.2011.5.25.32.4.1.2.12.1
    hwXQoSIfSoftCarEntry OBJECT-TYPE
        SYNTAX HwXQoSIfSoftCarEntry
        MAX-ACCESS not-accessible
        STATUS current
        DESCRIPTION
        "Interface software CAR  configuration  information entry."
        INDEX { hwXQoSIfSoftCarIfIndex,hwXQoSIfSoftCarDirection }
        ::= { hwXQoSIfSoftCarTable 1 }

    HwXQoSIfSoftCarEntry ::=
        SEQUENCE {
            hwXQoSIfSoftCarIfIndex
                Integer32,
            hwXQoSIfSoftCarDirection
                DirectionType,
            hwXQoSIfSoftCarCarIndex
                Integer32,
            hwXQoSIfSoftCarRowStatus
                RowStatus
         }

    -- 1.3.6.1.4.1.2011.5.25.32.4.1.2.12.1.1
    hwXQoSIfSoftCarIfIndex OBJECT-TYPE
        SYNTAX Integer32
            MAX-ACCESS not-accessible
        STATUS current
        DESCRIPTION
        "Interface index,equal ifIndex."
        ::= { hwXQoSIfSoftCarEntry 1 }

    -- 1.3.6.1.4.1.2011.5.25.32.4.1.2.12.1.2
    hwXQoSIfSoftCarDirection OBJECT-TYPE
        SYNTAX DirectionType
            MAX-ACCESS not-accessible
        STATUS current
        DESCRIPTION
            "Policy direction:
            inbound (1)
            outbound (2)"
        ::= { hwXQoSIfSoftCarEntry 2 }

    -- 1.3.6.1.4.1.2011.5.25.32.4.1.2.12.1.3
    hwXQoSIfSoftCarCarIndex OBJECT-TYPE
            SYNTAX Integer32 (0..65534)
            MAX-ACCESS read-create
        STATUS current
        DESCRIPTION
        "Car index,refers to hwXQoSCpcarIndex."
        ::= { hwXQoSIfSoftCarEntry 3 }

    -- 1.3.6.1.4.1.2011.5.25.32.4.1.2.12.1.4
    hwXQoSIfSoftCarRowStatus OBJECT-TYPE
        SYNTAX RowStatus
        MAX-ACCESS read-create
        STATUS current
        DESCRIPTION
            "RowStatus. Three actions are used: active,
            createAndGo, destroy."
        ::= { hwXQoSIfSoftCarEntry 4 }

-- local-precedence-queue-map
    hwXQoSIfLocalPrecedenceQueueMapTable OBJECT-TYPE
        SYNTAX SEQUENCE OF HwXQoSIfLocalPrecedenceQueueMapEntry
        MAX-ACCESS not-accessible
        STATUS current
        DESCRIPTION
            "A table of local precedence to queue map information."
        ::= { hwXQoSIfActionObjects 13 }


    hwXQoSIfLocalPrecedenceQueueMapEntry OBJECT-TYPE
        SYNTAX HwXQoSIfLocalPrecedenceQueueMapEntry
        MAX-ACCESS not-accessible
        STATUS current
        DESCRIPTION
            "local precedence to queue map Information Entry."
        INDEX { hwXQoSIfLocPreQueMapIfIndex, hwXQoSIfLocPreQueMapPreValue}
        ::= { hwXQoSIfLocalPrecedenceQueueMapTable 1 }

    HwXQoSIfLocalPrecedenceQueueMapEntry ::=
        SEQUENCE {
            hwXQoSIfLocPreQueMapIfIndex
                Integer32,
            hwXQoSIfLocPreQueMapPreValue
               Integer32,
            hwXQoSIfLocPreQueMapCosType
                CosType,
            hwXQoSIfLocPreQueMapRowStatus
                RowStatus
         }

    hwXQoSIfLocPreQueMapIfIndex OBJECT-TYPE
        SYNTAX Integer32
        MAX-ACCESS read-only
        STATUS current
        DESCRIPTION
            "interface index "
        ::= { hwXQoSIfLocalPrecedenceQueueMapEntry 1 }

    hwXQoSIfLocPreQueMapPreValue OBJECT-TYPE
        SYNTAX Integer32(0..7)
        MAX-ACCESS read-only
        STATUS current
        DESCRIPTION
            " Local precedence value."
        ::= { hwXQoSIfLocalPrecedenceQueueMapEntry 2 }

    hwXQoSIfLocPreQueMapCosType OBJECT-TYPE
        SYNTAX CosType
        MAX-ACCESS read-write
        STATUS current
        DESCRIPTION
            "queue index"
        ::= { hwXQoSIfLocalPrecedenceQueueMapEntry 3 }

    hwXQoSIfLocPreQueMapRowStatus OBJECT-TYPE
        SYNTAX RowStatus
        MAX-ACCESS read-create
        STATUS current
        DESCRIPTION
            "RowStatus. Three actions are used: active,
            createAndGo, destroy"
        ::= { hwXQoSIfLocalPrecedenceQueueMapEntry  4 }

    hwXQoSIfScheduleModeCfgInfoTable OBJECT-TYPE
        SYNTAX SEQUENCE OF HwXQoSIfScheduleModeCfgInfoEntry
        MAX-ACCESS not-accessible
        STATUS current
        DESCRIPTION
            "A table of Schedule mode configuration information."
        ::= { hwXQoSIfActionObjects 14}

    hwXQoSIfScheduleModeCfgInfoEntry OBJECT-TYPE
        SYNTAX HwXQoSIfScheduleModeCfgInfoEntry
        MAX-ACCESS not-accessible
        STATUS current
        DESCRIPTION
            "Schedule mode Configuration Information Entry."
        INDEX { hwXQoSIfScheduleModeIfIndex }
        ::= { hwXQoSIfScheduleModeCfgInfoTable 1 }

    HwXQoSIfScheduleModeCfgInfoEntry ::=
        SEQUENCE {
            hwXQoSIfScheduleModeIfIndex
                Integer32,
            hwXQoSIfModeType
                INTEGER,
            hwXQoSIfScheduleModeRowStatus
                RowStatus
         }

    hwXQoSIfScheduleModeIfIndex OBJECT-TYPE
        SYNTAX Integer32
        MAX-ACCESS not-accessible
        STATUS current
        DESCRIPTION
            "Interface Index, equal to ifIndex."
        ::= { hwXQoSIfScheduleModeCfgInfoEntry 1 }

    hwXQoSIfModeType OBJECT-TYPE
        SYNTAX INTEGER
            {
             pqWfq(1),
             pq(2),
             wfq(3)
            }
        MAX-ACCESS read-create
        STATUS current
        DESCRIPTION
            "Schedule mode are PQ+WFQ(1), PQ(2) or WFQ(3)."
        ::= { hwXQoSIfScheduleModeCfgInfoEntry 2 }

    hwXQoSIfScheduleModeRowStatus OBJECT-TYPE
        SYNTAX RowStatus
        MAX-ACCESS read-create
        STATUS current
        DESCRIPTION
            "RowStatus. Three actions are used: active,
            createAndGo, destroy"
    ::= { hwXQoSIfScheduleModeCfgInfoEntry 3 }

    hwXQoSIfHQOSPriCfgInfoTable OBJECT-TYPE
        SYNTAX SEQUENCE OF HwXQoSIfHQOSPriCfgInfoEntry
        MAX-ACCESS not-accessible
        STATUS current
        DESCRIPTION
            "HQOS priority configure configuration table. "
        ::= { hwXQoSIfActionObjects 15}


    hwXQoSIfHQOSPriCfgInfoEntry OBJECT-TYPE
        SYNTAX HwXQoSIfHQOSPriCfgInfoEntry
        MAX-ACCESS not-accessible
        STATUS current
        DESCRIPTION
            "HQOS priority Configuration Information Entry."
        INDEX { hwXQoSIfHqosPriIfIndex }
        ::= { hwXQoSIfHQOSPriCfgInfoTable 1 }

    HwXQoSIfHQOSPriCfgInfoEntry ::=
        SEQUENCE {
            hwXQoSIfHqosPriIfIndex
                Integer32,
            hwXQoSIfHqosPriority
                INTEGER,
            hwXQoSIfHqosPriRowStatus
                RowStatus
         }

    hwXQoSIfHqosPriIfIndex OBJECT-TYPE
        SYNTAX Integer32
        MAX-ACCESS not-accessible
        STATUS current
        DESCRIPTION
            "Interface Index, equal to ifIndex."
        ::= { hwXQoSIfHQOSPriCfgInfoEntry 1 }

    hwXQoSIfHqosPriority OBJECT-TYPE
        SYNTAX INTEGER { be(1),af1(2),af2(3),af3(4),af4(5),ef(6),cs6(7),cs7(8)}
        MAX-ACCESS read-create
        STATUS current
        DESCRIPTION
            " be(1),af1(2),af2(3),af3(4),af4(5),ef(6),cs6(7),cs7(8)"
        ::= { hwXQoSIfHQOSPriCfgInfoEntry 2 }

    hwXQoSIfHqosPriRowStatus OBJECT-TYPE
        SYNTAX RowStatus
        MAX-ACCESS read-create
        STATUS current
        DESCRIPTION
            "RowStatus. Three actions are used: active,
            createAndGo, destroy"
    ::= { hwXQoSIfHQOSPriCfgInfoEntry 3 }

    hwXQoSIfOutboundMulticastCfgInfoTable OBJECT-TYPE
        SYNTAX SEQUENCE OF HwXQoSIfOutboundMulticastCfgInfoEntry
        MAX-ACCESS not-accessible
        STATUS current
        DESCRIPTION
            "Multicast outbound bandwidth table."
        ::= { hwXQoSIfActionObjects 16}

    hwXQoSIfOutboundMulticastCfgInfoEntry OBJECT-TYPE
        SYNTAX HwXQoSIfOutboundMulticastCfgInfoEntry
        MAX-ACCESS not-accessible
        STATUS current
        DESCRIPTION
            "Multicast outbound bandwidth Configuration Information Entry."
        INDEX { hwXQoSIfOutMulticastIfIndex }
        ::= { hwXQoSIfOutboundMulticastCfgInfoTable 1 }

    HwXQoSIfOutboundMulticastCfgInfoEntry ::=
        SEQUENCE {
            hwXQoSIfOutMulticastIfIndex
                Integer32,
            hwXQoSIfUnicastWeightValue
                Integer32,
            hwXQoSIfMulticastWeightValue
                Integer32,
            hwXQoSIfOutMulticastRowStatus
                RowStatus
         }

    hwXQoSIfOutMulticastIfIndex OBJECT-TYPE
        SYNTAX Integer32
        MAX-ACCESS not-accessible
        STATUS current
        DESCRIPTION
            "Interface Index, equal to ifIndex."
        ::= { hwXQoSIfOutboundMulticastCfgInfoEntry 1 }

    hwXQoSIfUnicastWeightValue OBJECT-TYPE
        SYNTAX Integer32 (0..15)
        MAX-ACCESS read-create
        STATUS current
        DESCRIPTION
            "Unicast weight value range(0~15)."
        ::= { hwXQoSIfOutboundMulticastCfgInfoEntry 2 }

    hwXQoSIfMulticastWeightValue OBJECT-TYPE
        SYNTAX Integer32 (0..15)
        MAX-ACCESS read-create
        STATUS current
        DESCRIPTION
            "Multicast weight value range(0~15). "
        ::= { hwXQoSIfOutboundMulticastCfgInfoEntry 3 }

    hwXQoSIfOutMulticastRowStatus OBJECT-TYPE
        SYNTAX RowStatus
        MAX-ACCESS read-create
        STATUS current
        DESCRIPTION
            "RowStatus. Three actions are used: active,
            createAndGo, destroy"
    ::= { hwXQoSIfOutboundMulticastCfgInfoEntry 4 }

--sRed
    hwXQoSIfSredCfgInfoTable OBJECT-TYPE
        SYNTAX SEQUENCE OF HwXQoSIfSredCfgInfoEntry
        MAX-ACCESS not-accessible
        STATUS current
        DESCRIPTION
            "A table of Sred configuration information."
        ::= { hwXQoSIfActionObjects 17 }

    hwXQoSIfSredCfgInfoEntry OBJECT-TYPE
        SYNTAX HwXQoSIfSredCfgInfoEntry
        MAX-ACCESS not-accessible
        STATUS current
        DESCRIPTION
            "Sred Configuration Information Entry."
        INDEX { hwXQoSIfSredQueueIndex }
        ::= { hwXQoSIfSredCfgInfoTable 1 }

    HwXQoSIfSredCfgInfoEntry ::=
        SEQUENCE {
            hwXQoSIfSredQueueIndex
                INTEGER,
            hwXQoSIfSredRedStartDiscardPoint
                Integer32,
            hwXQoSIfSredRedDiscardProbability
                INTEGER,
            hwXQoSIfSredYellowStartDiscardPoint
                Integer32,
            hwXQoSIfSredYellowDiscardProbability
                INTEGER,
            hwXQoSIfSredRowStatus
                RowStatus
         }

    hwXQoSIfSredQueueIndex OBJECT-TYPE
        SYNTAX INTEGER
        {
            be(1),
            af1(2),
            af2(3),
            af3(4),
            af4(5),
            ef(6),
            cs6(7),
            cs7(8)
        }
        MAX-ACCESS not-accessible
        STATUS current
        DESCRIPTION
            "The Sred queue index
             be(1),
             af1(2),
             af2(3),
             af3(4),
             af4(5),
             ef(6),
             cs6(7),
             cs7(8)"
        ::= { hwXQoSIfSredCfgInfoEntry 1 }

    hwXQoSIfSredRedStartDiscardPoint OBJECT-TYPE
        SYNTAX Integer32
        MAX-ACCESS read-create
        STATUS current
        DESCRIPTION
            "The Sred Red Start Discard Point.unit:packet"
        ::= { hwXQoSIfSredCfgInfoEntry 2 }

    hwXQoSIfSredRedDiscardProbability OBJECT-TYPE
        SYNTAX INTEGER
        {
            drop1(1),
            drop2(2),
            drop3(3),
            drop4(4),
            drop5(5),
            drop6(6),
            drop7(7),
            drop8(8)
        }
        MAX-ACCESS read-create
        STATUS current
        DESCRIPTION
            "The Sred Red Discard Probability.
             drop1(1) = 100%
             drop2(2) = 6.25%
             drop3(3) = 3.125%
             drop4(4) = 1.5625%
             drop5(5) = 0.78125%
             drop6(6) = 0.390625%
             drop7(7) = 0.1953125%
             drop8(8) = 0.09765625% "
        ::= { hwXQoSIfSredCfgInfoEntry 3 }

    hwXQoSIfSredYellowStartDiscardPoint OBJECT-TYPE
        SYNTAX Integer32
        MAX-ACCESS read-create
        STATUS current
        DESCRIPTION
            "The Sred Yellow Start Discard Point.unit:packet"
        ::= { hwXQoSIfSredCfgInfoEntry 4 }

    hwXQoSIfSredYellowDiscardProbability OBJECT-TYPE
        SYNTAX INTEGER
        {
            drop1(1),
            drop2(2),
            drop3(3),
            drop4(4),
            drop5(5),
            drop6(6),
            drop7(7),
            drop8(8)
        }
        MAX-ACCESS read-create
        STATUS current
        DESCRIPTION
            "The Sred Yellow Discard Probability.
             drop1(1) = 100%
             drop2(2) = 6.25%
             drop3(3) = 3.125%
             drop4(4) = 1.5625%
             drop5(5) = 0.78125%
             drop6(6) = 0.390625%
             drop7(7) = 0.1953125%
             drop8(8) = 0.09765625% "
        ::= { hwXQoSIfSredCfgInfoEntry 5 }

    hwXQoSIfSredRowStatus OBJECT-TYPE
        SYNTAX RowStatus
        MAX-ACCESS read-create
        STATUS current
        DESCRIPTION
            "RowStatus. Three actions are used: active,
            createAndGo, destroy"
        ::= { hwXQoSIfSredCfgInfoEntry 6 }

--add at 2007-12-10
    hwXQosAtmTrafficQueueTable OBJECT-TYPE
        SYNTAX SEQUENCE OF HwXQosAtmTrafficQueueEntry
        MAX-ACCESS not-accessible
        STATUS current
        DESCRIPTION
            "The table provides traffic classification."
        ::= { hwXQoSIfActionObjects 18 }

    hwXQosAtmTrafficQueueEntry OBJECT-TYPE
        SYNTAX HwXQosAtmTrafficQueueEntry
        MAX-ACCESS not-accessible
        STATUS current
        DESCRIPTION
            "Traffic classification entry."
        INDEX { hwXQoSAtmTrafficQueueIfIndex }
        ::= { hwXQosAtmTrafficQueueTable 1 }

    HwXQosAtmTrafficQueueEntry ::=
        SEQUENCE {
            hwXQoSAtmTrafficQueueIfIndex
                Unsigned32,
            hwXQoSAtmTrafficQueueServiceClass
                Integer32,
            hwXQoSAtmTrafficQueueRowStatus
                RowStatus
         }

    hwXQoSAtmTrafficQueueIfIndex OBJECT-TYPE
        SYNTAX Unsigned32
        MAX-ACCESS not-accessible
        STATUS current
        DESCRIPTION
            "Index of interface."
        ::= { hwXQosAtmTrafficQueueEntry 1 }

    hwXQoSAtmTrafficQueueServiceClass OBJECT-TYPE
        SYNTAX Integer32
        MAX-ACCESS read-create
        STATUS current
        DESCRIPTION
            "The service class of the ATM traffic queue."
        ::= { hwXQosAtmTrafficQueueEntry 2 }

    hwXQoSAtmTrafficQueueRowStatus OBJECT-TYPE
        SYNTAX RowStatus
        MAX-ACCESS read-create
        STATUS current
        DESCRIPTION
            "State of the row."
        ::= { hwXQosAtmTrafficQueueEntry 3 }

    hwXQoSAtmPvcServiceTypeTable OBJECT-TYPE
        SYNTAX SEQUENCE OF HwXQoSAtmPvcServiceTypeEntry
        MAX-ACCESS not-accessible
        STATUS current
        DESCRIPTION
            "The table provides ATM PVC service type."
        ::= { hwXQoSIfActionObjects 19 }

    hwXQoSAtmPvcServiceTypeEntry OBJECT-TYPE
        SYNTAX HwXQoSAtmPvcServiceTypeEntry
        MAX-ACCESS not-accessible
        STATUS current
        DESCRIPTION
            "ATM PVC service entry."
        INDEX { hwXQoSAtmPvcServiceTypeVpiIndex, hwXQoSAtmPvcServiceTypeVciIndex, hwXQoSAtmPvcServiceTypeIfIndex }
        ::= { hwXQoSAtmPvcServiceTypeTable 1 }

    HwXQoSAtmPvcServiceTypeEntry ::=
        SEQUENCE {
            hwXQoSAtmPvcServiceTypeIfIndex
                Unsigned32,
            hwXQoSAtmPvcServiceTypeVpiIndex
                Unsigned32,
            hwXQoSAtmPvcServiceTypeVciIndex
                Unsigned32,
            hwXQoSAtmPvcNameServiceTypeIndex
                OCTET STRING,
            hwXQoSAtmPvcServiceType
                Integer32,
            hwXQoSAtmPvcPcr
                Integer32,
            hwXQoSAtmPvcCdvt
                Integer32,
            hwXQoSAtmPvcVbrScr
                Integer32,
            hwXQoSAtmPvcVbrMbs
                Integer32,
            hwXQoSAtmPvcRowStatus
                RowStatus
        }

    hwXQoSAtmPvcServiceTypeIfIndex OBJECT-TYPE
        SYNTAX Unsigned32
        MAX-ACCESS not-accessible
        STATUS current
        DESCRIPTION
            "Index of interface."
        ::= { hwXQoSAtmPvcServiceTypeEntry 1 }

    hwXQoSAtmPvcServiceTypeVpiIndex OBJECT-TYPE
        SYNTAX Unsigned32
        MAX-ACCESS not-accessible
        STATUS current
        DESCRIPTION
            "VPI for PVC."
        ::= { hwXQoSAtmPvcServiceTypeEntry 2 }

    hwXQoSAtmPvcServiceTypeVciIndex OBJECT-TYPE
        SYNTAX Unsigned32
        MAX-ACCESS not-accessible
        STATUS current
        DESCRIPTION
            "VCI for PVC."
        ::= { hwXQoSAtmPvcServiceTypeEntry 3 }

    hwXQoSAtmPvcNameServiceTypeIndex OBJECT-TYPE
        SYNTAX OCTET STRING
        MAX-ACCESS read-only
        STATUS current
        DESCRIPTION
            "Name for PVC."
        ::= { hwXQoSAtmPvcServiceTypeEntry 4 }

    hwXQoSAtmPvcServiceType OBJECT-TYPE
        SYNTAX Integer32
        MAX-ACCESS read-create
        STATUS current
        DESCRIPTION
            "Type of the service."
        ::= { hwXQoSAtmPvcServiceTypeEntry 5 }

    hwXQoSAtmPvcPcr OBJECT-TYPE
        SYNTAX Integer32
        MAX-ACCESS read-create
        STATUS current
        DESCRIPTION
            "Peak rate for sending ATM cells."
        ::= { hwXQoSAtmPvcServiceTypeEntry 6 }

    hwXQoSAtmPvcCdvt OBJECT-TYPE
        SYNTAX Integer32
        MAX-ACCESS read-create
        STATUS current
        DESCRIPTION
            "Tolerance of cell delay changes."
        ::= { hwXQoSAtmPvcServiceTypeEntry 7 }

    hwXQoSAtmPvcVbrScr OBJECT-TYPE
        SYNTAX Integer32
        MAX-ACCESS read-create
        STATUS current
        DESCRIPTION
            "Sustainable Rate for Sending ATM Cells."
        ::= { hwXQoSAtmPvcServiceTypeEntry 8 }

    hwXQoSAtmPvcVbrMbs OBJECT-TYPE
        SYNTAX Integer32
        MAX-ACCESS read-create
        STATUS current
        DESCRIPTION
            "Maximum Burst Size for Sending ATM Cells."
        ::= { hwXQoSAtmPvcServiceTypeEntry 9 }

    hwXQoSAtmPvcRowStatus OBJECT-TYPE
        SYNTAX RowStatus
        MAX-ACCESS read-create
        STATUS current
        DESCRIPTION
            "State of the row."
        ::= { hwXQoSAtmPvcServiceTypeEntry 10 }

--Shaping
    hwXQoSIfShapingCfgInfoTable OBJECT-TYPE
        SYNTAX SEQUENCE OF HwXQoSIfShapingCfgInfoEntry
        MAX-ACCESS not-accessible
        STATUS current
        DESCRIPTION
            "A table of Shaping configuration information."
        ::= { hwXQoSIfActionObjects 20 }

    hwXQoSIfShapingCfgInfoEntry OBJECT-TYPE
        SYNTAX HwXQoSIfShapingCfgInfoEntry
        MAX-ACCESS not-accessible
        STATUS current
        DESCRIPTION
            "Shaping Configuration Information Entry."
        INDEX { hwXQoSIfShapingIfIndex,hwXQoSIfShapingQueueIndex}
        ::= { hwXQoSIfShapingCfgInfoTable 1 }

    HwXQoSIfShapingCfgInfoEntry ::=
        SEQUENCE {
            hwXQoSIfShapingIfIndex
                Integer32,
            hwXQoSIfShapingQueueIndex
                INTEGER,
            hwXQoSIfShapingQueueCir
                Integer32,
            hwXQoSIfShapingQueuePir
                Integer32,
            hwXQoSIfShapingRowStatus
                RowStatus
         }

    hwXQoSIfShapingIfIndex OBJECT-TYPE
        SYNTAX Integer32
        MAX-ACCESS not-accessible
        STATUS current
        DESCRIPTION
            "Interface Index, equal to ifIndex."
        ::= { hwXQoSIfShapingCfgInfoEntry 1 }

    hwXQoSIfShapingQueueIndex OBJECT-TYPE
        SYNTAX INTEGER
        {
            be(1),
            af1(2),
            af2(3),
            af3(4),
            af4(5),
            ef(6),
            cs6(7),
            cs7(8)
        }
        MAX-ACCESS not-accessible
        STATUS current
        DESCRIPTION
            "The Shaping queue index
             be(1),
             af1(2),
             af2(3),
             af3(4),
             af4(5),
             ef(6),
             cs6(7),
             cs7(8)"
        ::= { hwXQoSIfShapingCfgInfoEntry 2 }

    hwXQoSIfShapingQueueCir OBJECT-TYPE
        SYNTAX Integer32
        MAX-ACCESS read-create
        STATUS current
        DESCRIPTION
            "Committed Information Rate. Unit: kbps."
        ::= { hwXQoSIfShapingCfgInfoEntry 3 }

    hwXQoSIfShapingQueuePir OBJECT-TYPE
        SYNTAX Integer32
        MAX-ACCESS read-create
        STATUS current
        DESCRIPTION
            "Peak Information Rate. Unit: kbps.
            Only hardware QoS support this node."
        ::= { hwXQoSIfShapingCfgInfoEntry 4 }

    hwXQoSIfShapingRowStatus OBJECT-TYPE
        SYNTAX RowStatus
        MAX-ACCESS read-create
        STATUS current
        DESCRIPTION
            "RowStatus. Three actions are used: active,
            createAndGo, destroy"
        ::= { hwXQoSIfShapingCfgInfoEntry 5 }

    hwXQoSIfPppoeCfgInfoTable OBJECT-TYPE
        SYNTAX SEQUENCE OF HwXQoSIfPppoeCfgInfoEntry
        MAX-ACCESS not-accessible
        STATUS current
        DESCRIPTION
            "A table of PPPoE configuration information."
        ::= { hwXQoSIfActionObjects 21 }

    hwXQoSIfPppoeCfgInfoEntry OBJECT-TYPE
        SYNTAX HwXQoSIfPppoeCfgInfoEntry
        MAX-ACCESS not-accessible
        STATUS current
        DESCRIPTION
            "PPPoE configuration information entry."
        INDEX { hwXQoSIfPppoeIfIndex, hwXQoSIfPppoeMatchType, hwXQoSIfPppoeSourceMac, hwXQoSIfPppoeDestMac }
        ::= { hwXQoSIfPppoeCfgInfoTable 1 }

    HwXQoSIfPppoeCfgInfoEntry ::=
        SEQUENCE {
            hwXQoSIfPppoeIfIndex
                Integer32,
            hwXQoSIfPppoeMatchType
                Integer32,
            hwXQoSIfPppoeSourceMac
                MacAddress,
            hwXQoSIfPppoeDestMac
                MacAddress,
            hwXQoSIfPppoeRowStatus
                RowStatus
         }

    hwXQoSIfPppoeIfIndex OBJECT-TYPE
        SYNTAX Integer32 (1..2147483647)
        MAX-ACCESS not-accessible
        STATUS current
        DESCRIPTION
            "Interface index, equal to ifIndex."
        ::= { hwXQoSIfPppoeCfgInfoEntry 1 }

    hwXQoSIfPppoeMatchType OBJECT-TYPE
        SYNTAX Integer32 (1..4)
        MAX-ACCESS not-accessible
        STATUS current
        DESCRIPTION
            "Match type: 1.any 2.source MAC 3.dest MAC 4.source MAC and dest MAC."
        ::= { hwXQoSIfPppoeCfgInfoEntry 2 }

    hwXQoSIfPppoeSourceMac OBJECT-TYPE
        SYNTAX MacAddress
        MAX-ACCESS not-accessible
        STATUS current
        DESCRIPTION
            "Source MAC address."
        ::= { hwXQoSIfPppoeCfgInfoEntry 3 }

    hwXQoSIfPppoeDestMac OBJECT-TYPE
        SYNTAX MacAddress
        MAX-ACCESS not-accessible
        STATUS current
        DESCRIPTION
            "Destination MAC address."
        ::= { hwXQoSIfPppoeCfgInfoEntry 4 }

    hwXQoSIfPppoeRowStatus OBJECT-TYPE
        SYNTAX RowStatus
        MAX-ACCESS read-create
        STATUS current
        DESCRIPTION
            "Row status. Two actions are used: createAndGo, destroy"
        ::= { hwXQoSIfPppoeCfgInfoEntry 5 }

     hwXQoSIfScheduleCfgInfoTable OBJECT-TYPE
        SYNTAX SEQUENCE OF HwXQoSIfScheduleCfgInfoEntry
        MAX-ACCESS not-accessible
        STATUS current
        DESCRIPTION
            "A table of interface schedule configuration information."
        ::= { hwXQoSIfActionObjects 22 }

    hwXQoSIfScheduleCfgInfoEntry OBJECT-TYPE
        SYNTAX HwXQoSIfScheduleCfgInfoEntry
        MAX-ACCESS not-accessible
        STATUS current
        DESCRIPTION
            "Interface schedule configuration information entry."
        INDEX { hwXQoSIfScheduleIfIndex}
        ::= { hwXQoSIfScheduleCfgInfoTable 1 }

    HwXQoSIfScheduleCfgInfoEntry ::=
        SEQUENCE {
            hwXQoSIfScheduleIfIndex
                Integer32,
            hwXQoSIfScheduleProfile
                OCTET STRING,
            hwXQoSIfScheduleRowStatus
                RowStatus
         }

    hwXQoSIfScheduleIfIndex OBJECT-TYPE
        SYNTAX Integer32 (1..2147483647)
        MAX-ACCESS not-accessible
        STATUS current
        DESCRIPTION
            "Interface index, equal to ifIndex."
        ::= { hwXQoSIfScheduleCfgInfoEntry 1 }

    hwXQoSIfScheduleProfile OBJECT-TYPE
        SYNTAX OCTET STRING (SIZE (1..31))
        MAX-ACCESS read-create
        STATUS current
        DESCRIPTION
            "Name of schedule profile."
        ::= { hwXQoSIfScheduleCfgInfoEntry 2 }

    hwXQoSIfScheduleRowStatus OBJECT-TYPE
        SYNTAX RowStatus
        MAX-ACCESS read-create
        STATUS current
        DESCRIPTION
            "RowStatus. Three actions are used: active,
            createAndGo, destroy"
        ::= { hwXQoSIfScheduleCfgInfoEntry 51 }

--  IPCAR Instance on interface Table
 hwXQoSIfIPCarCfgInfoTable OBJECT-TYPE
        SYNTAX SEQUENCE OF HwXQoSIfIPCarCfgInfoEntry
        MAX-ACCESS not-accessible
        STATUS current
        DESCRIPTION
            "A table of IPCAR feature configuration information."
        ::= { hwXQoSIfActionObjects 23 }

    hwXQoSIfIPCarCfgInfoEntry OBJECT-TYPE
        SYNTAX HwXQoSIfIPCarCfgInfoEntry
        MAX-ACCESS not-accessible
        STATUS current
        DESCRIPTION
            "IPCAR Configuration Information Entry."
        INDEX { hwXQoSIfIPCarCfgIfIndex, hwXQoSIfIPCarDirection, hwXQoSIPCarRuleIndex }
        ::= { hwXQoSIfIPCarCfgInfoTable 1 }

    HwXQoSIfIPCarCfgInfoEntry ::=
        SEQUENCE {
            hwXQoSIfIPCarCfgIfIndex
                Integer32,
            hwXQoSIfIPCarDirection
                DirectionType,
            hwXQoSIPCarRuleIndex
                Integer32,
            hwXQoSIPCarRuleType
                IPCARRuleType,
            hwXBQoSIPCarIntValue
                Unsigned32,
            hwXQoSIfIPCarStartIp
                IpAddress,
            hwXQoSIfIPCarEndIp
                IpAddress,
            hwXQoSIfIPCarCir
                Integer32,
            hwXQoSIfIPCarCbs
                Integer32,
            hwXQoSIfIPCarEbs
                Integer32,
            hwXQoSIfIPCarPir
                Integer32,
            hwXQoSIfIPCarPbs
                Integer32,
            hwXQoSIfIPCarGreenAction
                CarAction,
            hwXQoSIfIPCarGreenRemarkValue
                Integer32,
            hwXQoSIfIPCarYellowAction
                CarAction,
            hwXQoSIfIPCarYellowRemarkValue
                Integer32,
            hwXQoSIfIPCarRedAction
                CarAction,
            hwXQoSIfIPCarRedRemarkValue
                Integer32,
            hwXQoSIfIPCarAggregation
                INTEGER,
            hwXQoSIfIPCarRowStatus
                RowStatus
         }

    hwXQoSIfIPCarCfgIfIndex OBJECT-TYPE
        SYNTAX Integer32
        MAX-ACCESS read-only
        STATUS current
        DESCRIPTION
            "Interface Index, equal to ifIndex.
            This object has no default value."
        ::= { hwXQoSIfIPCarCfgInfoEntry 1 }

    hwXQoSIfIPCarDirection OBJECT-TYPE
        SYNTAX DirectionType
        MAX-ACCESS read-only
        STATUS current
        DESCRIPTION
            "IPCAR Rule direction:
            inbound (1)
            outbound (2)"
        ::= { hwXQoSIfIPCarCfgInfoEntry 2 }

    hwXQoSIPCarRuleIndex OBJECT-TYPE
        SYNTAX Integer32
        MAX-ACCESS read-only
        STATUS current
        DESCRIPTION
             "The value of this object identifies the index of IPCAR Rule.
             The value ranges from 0 to 254.
             This object has no default value."
        ::= { hwXQoSIfIPCarCfgInfoEntry 3 }

    hwXQoSIPCarRuleType OBJECT-TYPE
            SYNTAX IPCARRuleType
            MAX-ACCESS read-create
            STATUS current
            DESCRIPTION
                "The value of this object identifies the rule type.
                The value of this object can be any of the following:
                ipv4-acl(1)
                ipv4-SrcIp(2)
                ipv4-DstIp(3)
                This object has no default value."
        ::= { hwXQoSIfIPCarCfgInfoEntry 4 }

    hwXBQoSIPCarIntValue OBJECT-TYPE
            SYNTAX Unsigned32
            MAX-ACCESS read-create
            STATUS current
            DESCRIPTION
                "This object indicates the rule contents. The value range and the default value of the object vary with hwXQoSIPCarRuleType.
                 When the supported type is ipv4-acl(2), the value of this object ranges from 2000 to 4999.
                 This object has no default value."
            ::= { hwXQoSIfIPCarCfgInfoEntry 5 }

    hwXQoSIfIPCarStartIp OBJECT-TYPE
        SYNTAX IpAddress
        MAX-ACCESS read-create
        STATUS current
        DESCRIPTION
            "The object indicates the start of source IP address segment.
            This object has no default value.
            0.0.0.0 is invalid value."
         ::= { hwXQoSIfIPCarCfgInfoEntry 6 }

    hwXQoSIfIPCarEndIp OBJECT-TYPE
        SYNTAX IpAddress
        MAX-ACCESS read-create
        STATUS current
        DESCRIPTION
            "The object indicates the end of source IP address segment.
            This object has no default value.
            0.0.0.0 is invalid value."
         ::= { hwXQoSIfIPCarCfgInfoEntry 7 }

    hwXQoSIfIPCarCir OBJECT-TYPE
        SYNTAX Integer32
        MAX-ACCESS read-create
        STATUS current
        DESCRIPTION
            "Committed Information Rate. Unit: kbps.
            The value ranges from 8 to 4294967295, with no default value."
        ::= { hwXQoSIfIPCarCfgInfoEntry 8 }

    hwXQoSIfIPCarCbs OBJECT-TYPE
        SYNTAX Integer32
        MAX-ACCESS read-create
        STATUS current
        DESCRIPTION
            "Committed Burst Size. Unit: byte
            The value ranges from 1500 to 4294967295 bytes."
        ::= { hwXQoSIfIPCarCfgInfoEntry 9 }

    hwXQoSIfIPCarEbs OBJECT-TYPE
        SYNTAX Integer32
        MAX-ACCESS read-create
        STATUS current
        DESCRIPTION
            "Excess Burst Size. Unit: byte.
            Only software QoS support this node.
            -1 is returned only when getting value from hardware QoS.
            -1 can't be set."
        DEFVAL { 0 }
        ::= { hwXQoSIfIPCarCfgInfoEntry 10 }

    hwXQoSIfIPCarPir OBJECT-TYPE
        SYNTAX Integer32
        MAX-ACCESS read-create
        STATUS current
        DESCRIPTION
            "Peak Information Rate. Unit: kbps.
            The value ranges from 8 to 4294967295"
        ::= { hwXQoSIfIPCarCfgInfoEntry 11 }

    hwXQoSIfIPCarPbs OBJECT-TYPE
        SYNTAX Integer32
        MAX-ACCESS read-create
        STATUS current
        DESCRIPTION
            "Peak Burst Size. Unit: byte.
            The value ranges from 1500 to 4294967295 bytes."
        ::= { hwXQoSIfIPCarCfgInfoEntry 12 }

    hwXQoSIfIPCarGreenAction OBJECT-TYPE
        SYNTAX CarAction
        MAX-ACCESS read-create
        STATUS current
        DESCRIPTION
            "The value of this object identifies the action adopted when CIR is not reached.
                 pass (1),
                 discard (2),
                 remark IP Precedence (3),
                 remark DSCP(4),
                 remark Mpls Exp(5),
                 remark (6),
                 remark 8021p(7)
                 The default value is pass (1).
                 "
        DEFVAL { pass }
        ::= { hwXQoSIfIPCarCfgInfoEntry 13 }

    hwXQoSIfIPCarGreenRemarkValue OBJECT-TYPE
        SYNTAX Integer32 (-1 | 0..63)
        MAX-ACCESS read-create
        STATUS current
        DESCRIPTION
            "The value is to remark When green action is remarking.
            For remarking DSCP, the range is 0~63;
            For remarking IP Precedence and MPLS EXP, the range is 0~7;
            Only software QoS support this node.
            -1 is returned only when getting value from hardware QoS or when action being pass,discard of software QoS.
            -1 can't be set."
        ::= { hwXQoSIfIPCarCfgInfoEntry 14 }

    hwXQoSIfIPCarYellowAction OBJECT-TYPE
        SYNTAX CarAction
        MAX-ACCESS read-create
        STATUS current
        DESCRIPTION
            "The value of this object identifies the action adopted when CIR is exceeded but PIR is not reached.
                 pass (1),
                 discard (2),
                 remark IP Precedence (3),
                 remark DSCP(4),
                 remark Mpls Exp(5),
                 remark (6),
                 remark 8021p(7)
                 The default value is pass (1).
                 "
        DEFVAL { pass }
        ::= { hwXQoSIfIPCarCfgInfoEntry 15 }

    hwXQoSIfIPCarYellowRemarkValue OBJECT-TYPE
        SYNTAX Integer32 (-1 | 0..63)
        MAX-ACCESS read-create
        STATUS current
        DESCRIPTION
            "The value is to remark When yellow action is remarking.
            For remarking DSCP, the range is 0~63;
            For remarking IP Precedence and MPLS EXP, the range is 0~7;
            Only software QoS support this node.
            -1 is returned only when getting value from hardware QoS or when action being pass,discard of software QoS.
            -1 can't be set."
        ::= { hwXQoSIfIPCarCfgInfoEntry 16 }

    hwXQoSIfIPCarRedAction OBJECT-TYPE
        SYNTAX CarAction
        MAX-ACCESS read-create
        STATUS current
        DESCRIPTION
            "The value of this object identifies the action adopted when CIR is exceeded but PIR is not reached.
                 pass (1),
                 discard (2),
                 remark IP Precedence (3),
                 remark DSCP(4),
                 remark Mpls Exp(5),
                 remark (6),
                 remark 8021p(7)
                 The default value is pass (1).
                 "
        DEFVAL { discard }
        ::= { hwXQoSIfIPCarCfgInfoEntry 17 }

    hwXQoSIfIPCarRedRemarkValue OBJECT-TYPE
        SYNTAX Integer32 (-1 | 0..63)
        MAX-ACCESS read-create
        STATUS current
        DESCRIPTION
            "The value is to remark When red action is remarking.
            For remarking DSCP, the range is 0~63;
            For remarking IP Precedence and MPLS EXP, the range is 0~7;
            Only software QoS support this node.
            -1 is returned only when getting value from hardware QoS or when action being pass,discard of software QoS.
            -1 can't be set."
        ::= { hwXQoSIfIPCarCfgInfoEntry 18 }

     hwXQoSIfIPCarAggregation OBJECT-TYPE
         SYNTAX INTEGER
         {
            aggregationCar(1),
            noneAggregationCar(2)
         }
         MAX-ACCESS read-create
         STATUS current
         DESCRIPTION
            "aggregationCar(1): aggregation car;
            noneAggregationCar(2) : none aggregation car."
          ::= { hwXQoSIfIPCarCfgInfoEntry 19 }

    hwXQoSIfIPCarRowStatus OBJECT-TYPE
        SYNTAX RowStatus
        MAX-ACCESS read-create
        STATUS current
        DESCRIPTION
            "RowStatus. Three actions are used: active,
            createAndGo, destroy"
        ::= { hwXQoSIfIPCarCfgInfoEntry 20 }

-- 8021P CAR
    hwXQoSIf8021PCarCfgInfoTable OBJECT-TYPE
    SYNTAX SEQUENCE OF HwXQoSIf8021PCarCfgInfoEntry
    MAX-ACCESS not-accessible
    STATUS current
    DESCRIPTION
        "A table of 8021P CAR feature configuration information."
    ::= { hwXQoSIfActionObjects 24 }

    hwXQoSIf8021PCarCfgInfoEntry OBJECT-TYPE
    SYNTAX HwXQoSIf8021PCarCfgInfoEntry
    MAX-ACCESS not-accessible
    STATUS current
    DESCRIPTION
        "8021P CAR Configuration Information Entry."
    INDEX { hwXQoSIf8021PCarIfIndex, hwXQoSIf8021PCarDirection, hwXQoSIf8021PCarIndexId }
    ::= { hwXQoSIf8021PCarCfgInfoTable 1 }

    HwXQoSIf8021PCarCfgInfoEntry ::=
        SEQUENCE {
            hwXQoSIf8021PCarIfIndex
                Integer32,
            hwXQoSIf8021PCarDirection
                INTEGER,
            hwXQoSIf8021PCarIndexId
                Integer32,
            hwXQoSIf8021PCarCir
                Unsigned32,
            hwXQoSIf8021PCarCbs
                Unsigned32,
            hwXQoSIf8021PCarPir
                Unsigned32,
            hwXQoSIf8021PCarPbs
                Unsigned32,
            hwXQoSIf8021PCar8021pValue
                OCTET STRING,
            hwXQoSIf8021PCarRowStatus
                RowStatus
        }

    hwXQoSIf8021PCarIfIndex OBJECT-TYPE
        SYNTAX Integer32
        MAX-ACCESS read-only
        STATUS current
        DESCRIPTION
            "Interface Index, equal to ifIndex."
        ::= { hwXQoSIf8021PCarCfgInfoEntry 1 }


    hwXQoSIf8021PCarDirection OBJECT-TYPE
        SYNTAX INTEGER
            {
            inbound(1),
            outbound(2)
            }
        MAX-ACCESS read-only
        STATUS current
        DESCRIPTION
            "Apply direction:inbound (1),outbound (2)."
        ::= { hwXQoSIf8021PCarCfgInfoEntry 2 }


    hwXQoSIf8021PCarIndexId OBJECT-TYPE
        SYNTAX Integer32 (0..7)
        MAX-ACCESS read-only
        STATUS current
        DESCRIPTION
            "Every Command Index ID."
        ::= { hwXQoSIf8021PCarCfgInfoEntry 3 }


    hwXQoSIf8021PCarCir OBJECT-TYPE
        SYNTAX Unsigned32 (64..4294967295)
        MAX-ACCESS read-create
        STATUS current
        DESCRIPTION
            "Committed Information Rate. Unit: kbps.
                Unsigned32<64-4294967295> "
        ::= { hwXQoSIf8021PCarCfgInfoEntry 4 }


    hwXQoSIf8021PCarCbs OBJECT-TYPE
        SYNTAX Unsigned32 (1500..4294967295)
        MAX-ACCESS read-create
        STATUS current
        DESCRIPTION
            "Committed Burst Size. Unit: byte
                Unsigned32<1500-4294967295> "
        ::= { hwXQoSIf8021PCarCfgInfoEntry 5 }


    hwXQoSIf8021PCarPir OBJECT-TYPE
        SYNTAX Unsigned32 (64..4294967295)
        MAX-ACCESS read-create
        STATUS current
        DESCRIPTION
            "Peak Information Rate. Unit: kbps.
            Unsigned32<64-4294967295> "
        ::= { hwXQoSIf8021PCarCfgInfoEntry 6 }


    hwXQoSIf8021PCarPbs OBJECT-TYPE
        SYNTAX Unsigned32 (1500..4294967295)
        MAX-ACCESS read-create
        STATUS current
        DESCRIPTION
            "Peak Burst Size. Unit: byte.
                Unsigned32<1500-4294967295> "
        ::= { hwXQoSIf8021PCarCfgInfoEntry 7 }


    hwXQoSIf8021PCar8021pValue OBJECT-TYPE
        SYNTAX OCTET STRING (SIZE (0..31))
        MAX-ACCESS read-create
        STATUS current
        DESCRIPTION
            "VLAN 802.1p value.
            STRING<0-7> "
        ::= { hwXQoSIf8021PCarCfgInfoEntry 8 }


    hwXQoSIf8021PCarRowStatus OBJECT-TYPE
        SYNTAX RowStatus
        MAX-ACCESS read-create
        STATUS current
        DESCRIPTION
            "RowStatus. Three actions are used: active(1),
                createAndGo(4), destroy(6)."
        ::= { hwXQoSIf8021PCarCfgInfoEntry 9 }

--   Cpcar command
    hwXQoSCpcarObjects OBJECT IDENTIFIER ::= { hwXQoSObjects 3 }

--    Cp car
    hwXQoSCpcarCfgInfoTable OBJECT-TYPE
        SYNTAX SEQUENCE OF HwXQoSCpcarCfgInfoEntry
        MAX-ACCESS not-accessible
        STATUS current
        DESCRIPTION
            "A table of cp car configuration information."
        ::= { hwXQoSCpcarObjects 1 }

    hwXQoSCpcarCfgInfoEntry OBJECT-TYPE
        SYNTAX HwXQoSCpcarCfgInfoEntry
        MAX-ACCESS not-accessible
        STATUS current
        DESCRIPTION
            "Diff-server domain Information Entry."
        INDEX { hwXQoSCpcarIndex }
        ::= { hwXQoSCpcarCfgInfoTable 1 }

    HwXQoSCpcarCfgInfoEntry ::=
        SEQUENCE {
            hwXQoSCpcarIndex
                Integer32,
            hwXQoSCpcarName
                OCTET STRING,
            hwXQoSCpcarRowStatus
                RowStatus
         }

    hwXQoSCpcarIndex OBJECT-TYPE
        SYNTAX Integer32
        MAX-ACCESS read-only
        STATUS current
        DESCRIPTION
            "Index of cp car domain."
        ::= { hwXQoSCpcarCfgInfoEntry 1 }

    hwXQoSCpcarName OBJECT-TYPE
        SYNTAX OCTET STRING (SIZE (1..31))
        MAX-ACCESS read-create
        STATUS current
        DESCRIPTION
            "Exception name of cp car."
        ::= { hwXQoSCpcarCfgInfoEntry 2 }

    hwXQoSCpcarRowStatus OBJECT-TYPE
        SYNTAX RowStatus
        MAX-ACCESS read-create
        STATUS current
        DESCRIPTION
            "RowStatus. Three actions are used: active,
            createAndGo, destroy"
        ::= { hwXQoSCpcarCfgInfoEntry 3 }

--    filter in cp car
    hwXQoSCpCarFilterCfgInfoTable OBJECT-TYPE
        SYNTAX SEQUENCE OF HwXQoSCpCarFilterCfgInfoEntry
        MAX-ACCESS not-accessible
        STATUS current
        DESCRIPTION
            "A table of cpcar filter configuration information."
        ::= { hwXQoSCpcarObjects 2 }

    hwXQoSCpCarFilterCfgInfoEntry OBJECT-TYPE
        SYNTAX HwXQoSCpCarFilterCfgInfoEntry
        MAX-ACCESS not-accessible
        STATUS current
        DESCRIPTION
            "Diff-serve domain 8021p phb Configuration Information Entry."
        INDEX { hwXQoSCpcarIndex }
        ::= { hwXQoSCpCarFilterCfgInfoTable 1 }

    HwXQoSCpCarFilterCfgInfoEntry ::=
        SEQUENCE {
            hwXQoSCpCarFilterAction
                INTEGER,
            hwXQoSCpCarFilterRowStatus
                RowStatus
         }

    hwXQoSCpCarFilterAction OBJECT-TYPE
        SYNTAX INTEGER
        {
            pass(1),
            drop(2)
        }
        MAX-ACCESS read-only
        STATUS current
        DESCRIPTION
            "filter action
            1:pass
            2:drop
            DEFVAL { pass }"
        ::= { hwXQoSCpCarFilterCfgInfoEntry 1 }

    hwXQoSCpCarFilterRowStatus OBJECT-TYPE
        SYNTAX RowStatus
        MAX-ACCESS read-create
        STATUS current
        DESCRIPTION
            "RowStatus. Three actions are used: active,
            createAndGo, destroy"
        ::= { hwXQoSCpCarFilterCfgInfoEntry 2 }

--    CAR in cp car
    hwXQoSCpCarCfgInfoTable OBJECT-TYPE
        SYNTAX SEQUENCE OF HwXQoSCpCarCfgInfoEntry
        MAX-ACCESS not-accessible
        STATUS current
        DESCRIPTION
            "A table of CAR feature configuration information."
        ::= { hwXQoSCpcarObjects 3 }

    hwXQoSCpCarCfgInfoEntry OBJECT-TYPE
        SYNTAX HwXQoSCpCarCfgInfoEntry
        MAX-ACCESS not-accessible
        STATUS current
        DESCRIPTION
            "CAR Configuration Information Entry."
        INDEX { hwXQoSCpcarIndex }
        ::= { hwXQoSCpCarCfgInfoTable 1 }

    HwXQoSCpCarCfgInfoEntry ::=
        SEQUENCE {
            hwXQoSCpCarSlotId
                Integer32,
            hwXQoSCpCarCir
                Integer32,
            hwXQoSCpCarCbs
                Integer32,
            hwXQoSCpCarEbs
                Integer32,
            hwXQoSCpCarPir
                Integer32,
            hwXQoSCpCarPbs
                Integer32,
            hwXQoSCpCarGreenAction
                CarAction,
            hwXQoSCpCarGreenRemarkValue
                Integer32,
            hwXQoSCpCarYellowAction
                CarAction,
            hwXQoSCpCarYellowRemarkValue
                Integer32,
            hwXQoSCpCarRedAction
                CarAction,
            hwXQoSCpCarRedRemarkValue
                Integer32,
            hwXQoSCpCarRowStatus
                RowStatus
         }

    hwXQoSCpCarSlotId OBJECT-TYPE
        SYNTAX Integer32 (1..128)
        MAX-ACCESS read-create
        STATUS current
        DESCRIPTION
            "Target slot"
        ::= { hwXQoSCpCarCfgInfoEntry 1 }

    hwXQoSCpCarCir OBJECT-TYPE
        SYNTAX Integer32 (8..10000000)
        MAX-ACCESS read-create
        STATUS current
        DESCRIPTION
            "Committed Information Rate. Unit: kbps.
            software QoS: 8..155000
            hardware QoS: 100..10000000"
        ::= { hwXQoSCpCarCfgInfoEntry 2 }

    hwXQoSCpCarCbs OBJECT-TYPE
        SYNTAX Integer32 (64..19375000)
        MAX-ACCESS read-create
        STATUS current
        DESCRIPTION
            "Committed Burst Size. Unit: byte
            software QoS: 1875..19375000 (default:max(cir*125/2,1875))
            hardware QoS: 64..131071(default:12288)"
        ::= { hwXQoSCpCarCfgInfoEntry 3 }

    hwXQoSCpCarEbs OBJECT-TYPE
        SYNTAX Integer32 (-1 | 0..19375000)
        MAX-ACCESS read-create
        STATUS current
        DESCRIPTION
            "Excess Burst Size. Unit: byte. 0..19375000
            Only software QoS support this node.
            -1 is returned only when getting value from hardware QoS.
            -1 can't be set."
        DEFVAL { 0 }
        ::= { hwXQoSCpCarCfgInfoEntry 4 }

    hwXQoSCpCarPir OBJECT-TYPE
        SYNTAX Integer32 (-1 | 0 | 100..10000000)
        MAX-ACCESS read-create
        STATUS current
        DESCRIPTION
            "Peak Information Rate. Unit: kbps. 100..10000000
            Only hardware QoS support this node.
            -1 is returned only when getting value from software QoS.
            -1 can't be set.
            0 is the default value"
        ::= { hwXQoSCpCarCfgInfoEntry 5 }

    hwXQoSCpCarPbs OBJECT-TYPE
        SYNTAX Integer32 (-1 | 0 | 64..4000000)
        MAX-ACCESS read-create
        STATUS current
        DESCRIPTION
            "Peak Burst Size. Unit: byte.
            64..4000000.(default:cbs when Peak Information Rate configured)
            Only hardware QoS support this node.
            -1 is returned only when getting value from software QoS.
            -1 can't be set.
            0 is the default value"
        ::= { hwXQoSCpCarCfgInfoEntry 6 }

    hwXQoSCpCarGreenAction OBJECT-TYPE
        SYNTAX CarAction
        MAX-ACCESS read-create
        STATUS current
        DESCRIPTION
            "Green Action:
            pass (1)
            discard (2)
            remark IP Precedence (3)
            remark DSCP (4)
            remark MPLS EXP (5)
            remark (6)
            Hardware QoS : pass,discard,remark.
            Software QoS : pass,discard,remark IP Precedence,remark DSCP,remark MPLS EXP.
            "
        DEFVAL { pass }
        ::= { hwXQoSCpCarCfgInfoEntry 7 }

    hwXQoSCpCarGreenRemarkValue OBJECT-TYPE
        SYNTAX Integer32 (-1 | 0..63)
        MAX-ACCESS read-create
        STATUS current
        DESCRIPTION
            "The value is to remark When green action is remarking.
            For remarking DSCP, the range is 0~63;
            For remarking IP Precedence and MPLS EXP, the range is 0~7;
            Only software QoS support this node.
            -1 is returned only when getting value from hardware QoS or when action being pass,discard of software QoS.
            -1 can't be set."
        ::= { hwXQoSCpCarCfgInfoEntry 8 }

    hwXQoSCpCarYellowAction OBJECT-TYPE
        SYNTAX CarAction
        MAX-ACCESS read-create
        STATUS current
        DESCRIPTION
            "Yellow Action:
            unavailable(-1)
            pass (1)
            discard (2)
            remark IP Precedence (3)
            remark DSCP (4)
            remark MPLS EXP (5)
            remark(6)
            Only hardware QoS support this node.Hardware QoS support pass,discard,remark.
            -1 is returned only when getting value from software QoS.
            -1 can't be set."
        ::= { hwXQoSCpCarCfgInfoEntry 9 }

    hwXQoSCpCarYellowRemarkValue OBJECT-TYPE
        SYNTAX Integer32 (-1 | 0..63)
        MAX-ACCESS read-create
        STATUS current
        DESCRIPTION
            "The value is to remark When yellow action is remarking.
            For remarking DSCP, the range is 0~63;
            For remarking IP Precedence and MPLS EXP, the range is 0~7;
            Only software QoS support this node.
            -1 is returned only when getting value from hardware QoS or when action being pass,discard of software QoS.
            -1 can't be set."
        ::= { hwXQoSCpCarCfgInfoEntry 10 }

    hwXQoSCpCarRedAction OBJECT-TYPE
        SYNTAX CarAction
        MAX-ACCESS read-create
        STATUS current
        DESCRIPTION
            "Red Action:
            pass (1)
            discard (2)
            remark IP Precedence (3)
            remark DSCP (4)
            remark MPLS EXP (5)
            remark (6)
            Hardware QoS : pass,discard,remark.
            Software QoS : pass,discard,remark IP Precedence,remark DSCP,remark MPLS EXP.
            "
        DEFVAL { discard }
        ::= { hwXQoSCpCarCfgInfoEntry 11 }

    hwXQoSCpCarRedRemarkValue OBJECT-TYPE
        SYNTAX Integer32 (-1 | 0..63)
        MAX-ACCESS read-create
        STATUS current
        DESCRIPTION
            "The value is to remark When red action is remarking.
            For remarking DSCP, the range is 0~63;
            For remarking IP Precedence and MPLS EXP, the range is 0~7;
            Only software QoS support this node.
            -1 is returned only when getting value from hardware QoS or when action being pass,discard of software QoS.
            -1 can't be set."
        ::= { hwXQoSCpCarCfgInfoEntry 12 }

    hwXQoSCpCarRowStatus OBJECT-TYPE
        SYNTAX RowStatus
        MAX-ACCESS read-create
        STATUS current
        DESCRIPTION
            "RowStatus. Three actions are used: active,
            createAndGo, destroy"
        ::= { hwXQoSCpCarCfgInfoEntry 13 }

--    Policy Instance in cp car
    hwXQoSCpApplyPolicyTable OBJECT-TYPE
        SYNTAX SEQUENCE OF HwXQoSCpApplyPolicyEntry
        MAX-ACCESS not-accessible
        STATUS current
        DESCRIPTION
            "A table of QoS policy instance."
        ::= { hwXQoSCpcarObjects 4 }

    hwXQoSCpApplyPolicyEntry OBJECT-TYPE
        SYNTAX HwXQoSCpApplyPolicyEntry
        MAX-ACCESS not-accessible
        STATUS current
        DESCRIPTION
            "Policy applied on Ethernet Vlan Configuration Information Entry."
        INDEX { hwXQoSCpcarIndex }
        ::= { hwXQoSCpApplyPolicyTable 1 }

    HwXQoSCpApplyPolicyEntry ::=
        SEQUENCE {
            hwXQoSCpApplyPolicyName
                OCTET STRING,
            hwXQoSCpApplyPolicyRowStatus
                RowStatus
         }

    hwXQoSCpApplyPolicyName OBJECT-TYPE
        SYNTAX OCTET STRING (SIZE (1..127))
        MAX-ACCESS read-create
        STATUS current
        DESCRIPTION
            "Name of Traffic Policy."
        ::= { hwXQoSCpApplyPolicyEntry 1 }

    hwXQoSCpApplyPolicyRowStatus OBJECT-TYPE
        SYNTAX RowStatus
        MAX-ACCESS read-create
        STATUS current
        DESCRIPTION
            "RowStatus. Three actions are used: active,
            createAndGo, destroy"
        ::= { hwXQoSCpApplyPolicyEntry 2 }

    -- 1.3.6.1.4.1.2011.5.25.32.4.1.3.5
    hwXQoSCpCarActionTable OBJECT-TYPE
        SYNTAX SEQUENCE OF HwXQoSCpCarActionEntry
        MAX-ACCESS not-accessible
        STATUS current
        DESCRIPTION
            "A table of cp car action configuration information."
        ::= { hwXQoSCpcarObjects 5 }

    -- 1.3.6.1.4.1.2011.5.25.32.4.1.3.5.1
    hwXQoSCpCarActionEntry OBJECT-TYPE
        SYNTAX HwXQoSCpCarActionEntry
        MAX-ACCESS not-accessible
        STATUS current
        DESCRIPTION
            "Cp car action configuration information entry."
        INDEX { hwXQoSCpCarActionSlotIndex, hwXQoSCpCarActionPacketType }
        ::= { hwXQoSCpCarActionTable 1 }

    HwXQoSCpCarActionEntry ::=
        SEQUENCE {
            hwXQoSCpCarActionSlotIndex
                Integer32,
            hwXQoSCpCarActionPacketType
                    Integer32,
            hwXQoSCpCarActionPacketTypeName
                OCTET STRING,
            hwXQoSCpCarActionType
                BITS,
            hwXQoSCpCarActionPolicyName
                OCTET STRING,
            hwXQoSCpCarActionCarCir
                Integer32,
            hwXQoSCpCarActionCarCbs
                Integer32,
            hwXQoSCpCarActionCarEbs
                Integer32,
            hwXQoSCpCarActionCarPir
                Integer32,
            hwXQoSCpCarActionCarPbs
                Integer32,
            hwXQoSCpCarActionGreenAction
                CarAction,
            hwXQoSCpCarActionGreenRemarkValue
                Integer32,
            hwXQoSCpCarActionYellowAction
                CarAction,
            hwXQoSCpCarActionYellowRemarkValue
                Integer32,
            hwXQoSCpCarActionRedAction
                CarAction,
            hwXQoSCpCarActionRedRemarkValue
                Integer32,
            hwXQoSCpCarActionSetDefault
                Integer32
         }

    -- 1.3.6.1.4.1.2011.5.25.32.4.1.3.5.1.1
    hwXQoSCpCarActionSlotIndex OBJECT-TYPE
        SYNTAX Integer32
        MAX-ACCESS not-accessible
        STATUS current
        DESCRIPTION
            "Slot index."
        ::= { hwXQoSCpCarActionEntry 1 }

    -- 1.3.6.1.4.1.2011.5.25.32.4.1.3.5.1.2
    hwXQoSCpCarActionPacketType OBJECT-TYPE
        SYNTAX Integer32
        MAX-ACCESS not-accessible
        STATUS current
        DESCRIPTION
            "Packet type."
        ::= { hwXQoSCpCarActionEntry 2 }

    -- 1.3.6.1.4.1.2011.5.25.32.4.1.3.5.1.3
    hwXQoSCpCarActionPacketTypeName OBJECT-TYPE
        SYNTAX OCTET STRING (SIZE (1..31))
        MAX-ACCESS read-only
        STATUS current
        DESCRIPTION
            "Name of packet type."
        ::= { hwXQoSCpCarActionEntry 3 }

    -- 1.3.6.1.4.1.2011.5.25.32.4.1.3.5.1.4
    hwXQoSCpCarActionType OBJECT-TYPE
        SYNTAX BITS
            {
            pass(0),
            discard(1),
            car(2),
            trafficPolicy(3)
            }
        MAX-ACCESS read-write
        STATUS current
        DESCRIPTION
            "Action type."
        ::= { hwXQoSCpCarActionEntry 4 }

        -- 1.3.6.1.4.1.2011.5.25.32.4.1.3.5.1.5
    hwXQoSCpCarActionPolicyName OBJECT-TYPE
        SYNTAX OCTET STRING (SIZE (0..127))
        MAX-ACCESS read-write
        STATUS current
        DESCRIPTION
            "Policy Name"
        DEFVAL { "" }
        ::= { hwXQoSCpCarActionEntry 5 }

     -- 1.3.6.1.4.1.2011.5.25.32.4.1.3.5.1.6
    hwXQoSCpCarActionCarCir OBJECT-TYPE
        SYNTAX Integer32
        MAX-ACCESS read-write
        STATUS current
        DESCRIPTION
            "Committed Information Rate. Unit: kbps."
        DEFVAL { -1 }
        ::= { hwXQoSCpCarActionEntry 6 }

    -- 1.3.6.1.4.1.2011.5.25.32.4.1.3.5.1.7
    hwXQoSCpCarActionCarCbs OBJECT-TYPE
        SYNTAX Integer32
        MAX-ACCESS read-write
        STATUS current
        DESCRIPTION
            "Committed Burst Size. Unit: byte"
        DEFVAL { -1 }
        ::= { hwXQoSCpCarActionEntry 7 }

        hwXQoSCpCarActionCarEbs OBJECT-TYPE
        SYNTAX Integer32
        MAX-ACCESS read-write
        STATUS current
        DESCRIPTION
            "Excess Burst Size. Unit: byte."
        DEFVAL { -1}
        ::= { hwXQoSCpCarActionEntry 8 }

    -- 1.3.6.1.4.1.2011.5.25.32.4.1.3.5.1.9
    hwXQoSCpCarActionCarPir OBJECT-TYPE
        SYNTAX Integer32
        MAX-ACCESS read-write
        STATUS current
        DESCRIPTION
            "Peak Information Rate. Unit: kbps."
        DEFVAL { -1 }
        ::= { hwXQoSCpCarActionEntry 9 }

    -- 1.3.6.1.4.1.2011.5.25.32.4.1.3.5.1.10
    hwXQoSCpCarActionCarPbs OBJECT-TYPE
        SYNTAX Integer32
        MAX-ACCESS read-write
        STATUS current
        DESCRIPTION
            "Peak Burst Size. Unit: byte."
        DEFVAL { -1 }
        ::= { hwXQoSCpCarActionEntry 10 }

    -- 1.3.6.1.4.1.2011.5.25.32.4.1.3.5.1.11
    hwXQoSCpCarActionGreenAction OBJECT-TYPE
        SYNTAX CarAction
        MAX-ACCESS read-write
        STATUS current
        DESCRIPTION
            "Green Action.
            pass (1)
            discard (2)
            remark IP Precedence (3)
            remark DSCP (4)
            remark MPLS EXP (5)
            remark (6)
            Hardware QoS : pass,discard,remark.
            Software QoS : pass,discard,remark IP Precedence,remark DSCP,remark MPLS EXP."
        ::= { hwXQoSCpCarActionEntry 11 }

    -- 1.3.6.1.4.1.2011.5.25.32.4.1.3.5.1.12
    hwXQoSCpCarActionGreenRemarkValue OBJECT-TYPE
        SYNTAX Integer32 (-1 | 0..63)
        MAX-ACCESS read-write
        STATUS current
        DESCRIPTION
            "The value is to remark When green action is remarking.
            For remarking DSCP, the range is 0~63;
            For remarking IP Precedence and MPLS EXP, the range is 0~7;
            Only software QoS support this node.
            -1 is returned only when getting value from hardware QoS or when action being pass,discard of software QoS.
            -1 can't be set."
        ::= { hwXQoSCpCarActionEntry 12 }

    -- 1.3.6.1.4.1.2011.5.25.32.4.1.3.5.1.13
    hwXQoSCpCarActionYellowAction OBJECT-TYPE
        SYNTAX CarAction
        MAX-ACCESS read-write
        STATUS current
        DESCRIPTION
            "Yellow Action.
            pass (1)
            discard (2)
            remark IP Precedence (3)
            remark DSCP (4)
            remark MPLS EXP (5)
            remark (6)
            Hardware QoS : pass,discard,remark.
            Software QoS : pass,discard,remark IP Precedence,remark DSCP,remark MPLS EXP."
        ::= { hwXQoSCpCarActionEntry 13 }

    -- 1.3.6.1.4.1.2011.5.25.32.4.1.3.5.1.14
    hwXQoSCpCarActionYellowRemarkValue OBJECT-TYPE
        SYNTAX Integer32 (-1 | 0..63)
        MAX-ACCESS read-write
        STATUS current
        DESCRIPTION
            "The value is to remark When yellow action is remarking.
            For remarking DSCP, the range is 0~63;
            For remarking IP Precedence and MPLS EXP, the range is 0~7;
            Only software QoS support this node.
            -1 is returned only when getting value from hardware QoS or when action being pass,discard of software QoS.
            -1 can't be set."
        ::= { hwXQoSCpCarActionEntry 14 }

    -- 1.3.6.1.4.1.2011.5.25.32.4.1.3.5.1.15
    hwXQoSCpCarActionRedAction OBJECT-TYPE
        SYNTAX CarAction
        MAX-ACCESS read-write
        STATUS current
        DESCRIPTION
            "Red Action.
            pass (1)
            discard (2)
            remark IP Precedence (3)
            remark DSCP (4)
            remark MPLS EXP (5)
            remark (6)
            Hardware QoS : pass,discard,remark.
            Software QoS : pass,discard,remark IP Precedence,remark DSCP,remark MPLS EXP."
        ::= { hwXQoSCpCarActionEntry 15 }

    -- 1.3.6.1.4.1.2011.5.25.32.4.1.3.5.1.16
    hwXQoSCpCarActionRedRemarkValue OBJECT-TYPE
        SYNTAX Integer32 (-1 | 0..63)
        MAX-ACCESS read-write
        STATUS current
        DESCRIPTION
            "The value is to remark When red action is remarking.
            For remarking DSCP, the range is 0~63;
            For remarking IP Precedence and MPLS EXP, the range is 0~7;
            Only software QoS support this node.
            -1 is returned only when getting value from hardware QoS or when action being pass,discard of software QoS.
            -1 can't be set."
        ::= { hwXQoSCpCarActionEntry 16 }

    -- 1.3.6.1.4.1.2011.5.25.32.4.1.3.5.1.17
    hwXQoSCpCarActionSetDefault OBJECT-TYPE
        SYNTAX Integer32 (0..1)
        MAX-ACCESS read-write
        STATUS current
        DESCRIPTION
            "This OID is used for setting the CP CAR info to default.
            When you want to set the value to default, set this OID to 1."
        ::= { hwXQoSCpCarActionEntry 17 }

    -- 1.3.6.1.4.1.2011.5.25.32.4.1.4
    hwXQoSStatisticsObjects OBJECT IDENTIFIER ::= { hwXQoSObjects 4 }

--    Cp car statistics information
    hwXQoSCpcarStaticsObjects OBJECT IDENTIFIER ::= { hwXQoSStatisticsObjects 2 }


--    Cp car statistics
    hwXQoSCpcarRunInfoTable OBJECT-TYPE
        SYNTAX SEQUENCE OF HwXQoSCpcarRunInfoEntry
        MAX-ACCESS not-accessible
        STATUS current
        DESCRIPTION
            "A table of Running statistics for sample
            in a QoS policy applied on the interface."
        ::= { hwXQoSCpcarStaticsObjects 1 }

    hwXQoSCpcarRunInfoEntry OBJECT-TYPE
        SYNTAX HwXQoSCpcarRunInfoEntry
        MAX-ACCESS not-accessible
        STATUS current
        DESCRIPTION
            "Cp car statistics entry."
        INDEX { hwXQoSCpcarIndex }
        ::= { hwXQoSCpcarRunInfoTable 1 }

    HwXQoSCpcarRunInfoEntry ::=
        SEQUENCE {
            hwXQoSCpcarPassedPackets
                Counter64,
            hwXQoSCpcarPassededBytes
                Counter64,
            hwXQoSCpcarTotalPackets
                Counter64,
            hwXQoSCpcarTotalBytes
                Counter64,
            hwXQoSCpcarDiscardedPackets
                Counter64,
            hwXQoSCpcarDiscardedBytes
                Counter64
         }

    hwXQoSCpcarPassedPackets OBJECT-TYPE
        SYNTAX Counter64
        MAX-ACCESS read-only
        STATUS current
        DESCRIPTION
            "Number of packets passed of enqueue."
        ::= { hwXQoSCpcarRunInfoEntry 1 }

    hwXQoSCpcarPassededBytes OBJECT-TYPE
        SYNTAX Counter64
        MAX-ACCESS read-only
        STATUS current
        DESCRIPTION
            "Number of bytes passed of enqueue."
        ::= { hwXQoSCpcarRunInfoEntry 2 }

    hwXQoSCpcarTotalPackets OBJECT-TYPE
        SYNTAX Counter64
        MAX-ACCESS read-only
        STATUS current
        DESCRIPTION
            "Number of total packets."
        ::= { hwXQoSCpcarRunInfoEntry 3 }

    hwXQoSCpcarTotalBytes OBJECT-TYPE
        SYNTAX Counter64
        MAX-ACCESS read-only
        STATUS current
        DESCRIPTION
            "Number of total bytes."
        ::= { hwXQoSCpcarRunInfoEntry 4 }

    hwXQoSCpcarDiscardedPackets OBJECT-TYPE
        SYNTAX Counter64
        MAX-ACCESS read-only
        STATUS current
        DESCRIPTION
            "Number of packets discarded when enqueued by discard method."
        ::= { hwXQoSCpcarRunInfoEntry 5 }

    hwXQoSCpcarDiscardedBytes OBJECT-TYPE
        SYNTAX Counter64
        MAX-ACCESS read-only
        STATUS current
        DESCRIPTION
            "Number of bytes discarded when enqueued by discard method."
        ::= { hwXQoSCpcarRunInfoEntry 6 }

    -- 1.3.6.1.4.1.2011.5.25.32.4.1.4.2.2
    hwXQoSCpCarSlotStatTable OBJECT-TYPE
        SYNTAX SEQUENCE OF HwXQoSCpCarSlotStatEntry
        MAX-ACCESS not-accessible
        STATUS current
        DESCRIPTION
            "A table of Running statistics for sample
            in a QoS policy applied on the slot."
        ::= { hwXQoSCpcarStaticsObjects 2 }

    -- 1.3.6.1.4.1.2011.5.25.32.4.1.4.2.2.1
    hwXQoSCpCarSlotStatEntry OBJECT-TYPE
        SYNTAX HwXQoSCpCarSlotStatEntry
        MAX-ACCESS not-accessible
        STATUS current
        DESCRIPTION
            "Cp car on the slot statistics entry."
        INDEX { hwXQoSCpCarSlotStatSlotIndex, hwXQoSCpCarSlotStatPacketType }
        ::= { hwXQoSCpCarSlotStatTable 1 }

    HwXQoSCpCarSlotStatEntry ::=
        SEQUENCE {
            hwXQoSCpCarSlotStatSlotIndex
                Integer32,
            hwXQoSCpCarSlotStatPacketType
                Integer32,
            hwXQoSCpCarSlotStatDiscardedPackets
                Counter64,
            hwXQoSCpCarSlotStatDiscardedBytes
                Counter64,
            hwXQoSCpCarSlotStatPassedPackets
                Counter64,
            hwXQoSCpCarSlotStatPassededBytes
                Counter64,
            hwXQoSCpCarSlotStatTotalPackets
                Counter64,
            hwXQoSCpCarSlotStatTotalBytes
                Counter64
         }

    -- 1.3.6.1.4.1.2011.5.25.32.4.1.4.2.2.1.1
    hwXQoSCpCarSlotStatSlotIndex OBJECT-TYPE
        SYNTAX Integer32
        MAX-ACCESS not-accessible
        STATUS current
        DESCRIPTION
            "Slot index."
        ::= { hwXQoSCpCarSlotStatEntry 1 }

    -- 1.3.6.1.4.1.2011.5.25.32.4.1.4.2.2.1.2
    hwXQoSCpCarSlotStatPacketType OBJECT-TYPE
        SYNTAX Integer32
        MAX-ACCESS not-accessible
        STATUS current
        DESCRIPTION
            "Packet type."
        ::= { hwXQoSCpCarSlotStatEntry 2 }

    -- 1.3.6.1.4.1.2011.5.25.32.4.1.4.2.2.1.3
    hwXQoSCpCarSlotStatDiscardedPackets OBJECT-TYPE
        SYNTAX Counter64
        MAX-ACCESS read-only
        STATUS current
        DESCRIPTION
            "Number of packets discarded."
        ::= { hwXQoSCpCarSlotStatEntry 3 }

    -- 1.3.6.1.4.1.2011.5.25.32.4.1.4.2.2.1.4
    hwXQoSCpCarSlotStatDiscardedBytes OBJECT-TYPE
        SYNTAX Counter64
        MAX-ACCESS read-only
        STATUS current
        DESCRIPTION
            "Number of bytes discarded."
        ::= { hwXQoSCpCarSlotStatEntry 4 }

    -- 1.3.6.1.4.1.2011.5.25.32.4.1.4.2.2.1.5
    hwXQoSCpCarSlotStatPassedPackets OBJECT-TYPE
        SYNTAX Counter64
        MAX-ACCESS read-only
        STATUS current
        DESCRIPTION
            "Number of packets passed."
        ::= { hwXQoSCpCarSlotStatEntry 5 }

    -- 1.3.6.1.4.1.2011.5.25.32.4.1.4.2.2.1.6
    hwXQoSCpCarSlotStatPassededBytes OBJECT-TYPE
        SYNTAX Counter64
        MAX-ACCESS read-only
        STATUS current
        DESCRIPTION
            "Number of bytes passed."
        ::= { hwXQoSCpCarSlotStatEntry 6 }

    -- 1.3.6.1.4.1.2011.5.25.32.4.1.4.2.2.1.7
    hwXQoSCpCarSlotStatTotalPackets OBJECT-TYPE
        SYNTAX Counter64
        MAX-ACCESS read-only
        STATUS current
        DESCRIPTION
            "Number of total packets."
        ::= { hwXQoSCpCarSlotStatEntry 7 }

    -- 1.3.6.1.4.1.2011.5.25.32.4.1.4.2.2.1.8
    hwXQoSCpCarSlotStatTotalBytes OBJECT-TYPE
        SYNTAX Counter64
        MAX-ACCESS read-only
        STATUS current
        DESCRIPTION
            "Number of total bytes."
        ::= { hwXQoSCpCarSlotStatEntry 8 }

--    Interface statistics information
    hwXQoSIfStatisticsObjects OBJECT IDENTIFIER ::= { hwXQoSStatisticsObjects 3 }

--    CAR statistics
    hwXQoSIfCarRunInfoTable OBJECT-TYPE
        SYNTAX SEQUENCE OF HwXQoSIfCarRunInfoEntry
        MAX-ACCESS not-accessible
        STATUS current
        DESCRIPTION
            "A table of statistics for CAR on the interface."
        ::= { hwXQoSIfStatisticsObjects 1 }

    hwXQoSIfCarRunInfoEntry OBJECT-TYPE
        SYNTAX HwXQoSIfCarRunInfoEntry
        MAX-ACCESS not-accessible
        STATUS current
        DESCRIPTION
            "CAR statistics information entry."
        INDEX { hwXQoSIfCarIndex, hwXQoSIfVlanID }
        ::= { hwXQoSIfCarRunInfoTable 1 }

    HwXQoSIfCarRunInfoEntry ::=
        SEQUENCE {
            hwXQoSIfCarIndex
                Integer32,
            hwXQoSIfVlanID
                Integer32,
            hwXQoSIfCarGreenPassedPackets
                Counter64,
            hwXQoSIfCarGreenPassedBytes
                Counter64,
            hwXQoSIfCarGreenRemarkedPackets
                Counter64,
            hwXQoSIfCarGreenRemarkedBytes
                Counter64,
            hwXQoSIfCarGreenDiscardedPackets
                Counter64,
            hwXQoSIfCarGreenDiscardedBytes
                Counter64,
            hwXQoSIfCarYellowPassedPackets
                Counter64,
            hwXQoSIfCarYellowPassedBytes
                Counter64,
            hwXQoSIfCarYellowRemarkedPackets
                Counter64,
            hwXQoSIfCarYellowRemarkedBytes
                Counter64,
            hwXQoSIfCarYellowDiscardedPackets
                Counter64,
            hwXQoSIfCarYellowDiscardedBytes
                Counter64,
            hwXQoSIfCarRedPassedPackets
                Counter64,
            hwXQoSIfCarRedPassedBytes
                Counter64,
            hwXQoSIfCarRedRemarkedPackets
                Counter64,
            hwXQoSIfCarRedRemarkedBytes
                Counter64,
            hwXQoSIfCarRedDiscardedPackets
                Counter64,
            hwXQoSIfCarRedDiscardedBytes
                Counter64,
            hwXQoSIfCarTotalDiscardPackets
                Counter64,
            hwXQoSIfCarInBoundDiscardPackets
                Counter64,
            hwXQoSIfCarOutBoundDiscardPackets
                Counter64
         }

    hwXQoSIfCarIndex OBJECT-TYPE
        SYNTAX Integer32
        MAX-ACCESS read-only
        STATUS current
        DESCRIPTION
            "Interface Index, equal to ifIndex."
        ::= { hwXQoSIfCarRunInfoEntry 1 }

    hwXQoSIfVlanID OBJECT-TYPE
        SYNTAX Integer32 (0 | 1..4095)
        MAX-ACCESS read-only
        STATUS current
        DESCRIPTION
            "Vlan ID.
            -1 can't be set.
            0 is the default value"
        ::= { hwXQoSIfCarRunInfoEntry 2 }

    hwXQoSIfCarGreenPassedPackets OBJECT-TYPE
        SYNTAX Counter64
        MAX-ACCESS read-only
        STATUS current
        DESCRIPTION
            "Number of green packets passed."
        ::= { hwXQoSIfCarRunInfoEntry 3 }

    hwXQoSIfCarGreenPassedBytes OBJECT-TYPE
        SYNTAX Counter64
        MAX-ACCESS read-only
        STATUS current
        DESCRIPTION
            "Number of bytes green packets passed."
        ::= { hwXQoSIfCarRunInfoEntry 4 }

    hwXQoSIfCarGreenRemarkedPackets OBJECT-TYPE
        SYNTAX Counter64
        MAX-ACCESS read-only
        STATUS current
        DESCRIPTION
            "Number of green remarked packets."
        ::= { hwXQoSIfCarRunInfoEntry 5 }

    hwXQoSIfCarGreenRemarkedBytes OBJECT-TYPE
        SYNTAX Counter64
        MAX-ACCESS read-only
        STATUS current
        DESCRIPTION
            "Number of bytes green packets remarked."
        ::= { hwXQoSIfCarRunInfoEntry 6 }

    hwXQoSIfCarGreenDiscardedPackets OBJECT-TYPE
        SYNTAX Counter64
        MAX-ACCESS read-only
        STATUS current
        DESCRIPTION
            "Number of packets discarded."
        ::= { hwXQoSIfCarRunInfoEntry 7 }

    hwXQoSIfCarGreenDiscardedBytes OBJECT-TYPE
        SYNTAX Counter64
        MAX-ACCESS read-only
        STATUS current
        DESCRIPTION
            "Number of bytes exceeding CIR."
        ::= { hwXQoSIfCarRunInfoEntry 8 }

    hwXQoSIfCarYellowPassedPackets OBJECT-TYPE
        SYNTAX Counter64
        MAX-ACCESS read-only
        STATUS current
        DESCRIPTION
            "Number of yellow packets passed."
        ::= { hwXQoSIfCarRunInfoEntry 9 }

    hwXQoSIfCarYellowPassedBytes OBJECT-TYPE
        SYNTAX Counter64
        MAX-ACCESS read-only
        STATUS current
        DESCRIPTION
            "Number of bytes yellow packets passed."
        ::= { hwXQoSIfCarRunInfoEntry 10 }

    hwXQoSIfCarYellowRemarkedPackets OBJECT-TYPE
        SYNTAX Counter64
        MAX-ACCESS read-only
        STATUS current
        DESCRIPTION
            "Number of yellow remarked packets."
        ::= { hwXQoSIfCarRunInfoEntry 11 }

    hwXQoSIfCarYellowRemarkedBytes OBJECT-TYPE
        SYNTAX Counter64
        MAX-ACCESS read-only
        STATUS current
        DESCRIPTION
            "Number of bytes yellow packets remarked."
        ::= { hwXQoSIfCarRunInfoEntry 12 }

    hwXQoSIfCarYellowDiscardedPackets OBJECT-TYPE
        SYNTAX Counter64
        MAX-ACCESS read-only
        STATUS current
        DESCRIPTION
            "Number of yellow discard packets."
        ::= { hwXQoSIfCarRunInfoEntry 13 }

    hwXQoSIfCarYellowDiscardedBytes OBJECT-TYPE
        SYNTAX Counter64
        MAX-ACCESS read-only
        STATUS current
        DESCRIPTION
            "Number of bytes exceeding CIR."
        ::= { hwXQoSIfCarRunInfoEntry 14 }

    hwXQoSIfCarRedPassedPackets OBJECT-TYPE
        SYNTAX Counter64
        MAX-ACCESS read-only
        STATUS current
        DESCRIPTION
            "Number of red passed packets."
        ::= { hwXQoSIfCarRunInfoEntry 15 }

    hwXQoSIfCarRedPassedBytes OBJECT-TYPE
        SYNTAX Counter64
        MAX-ACCESS read-only
        STATUS current
        DESCRIPTION
            "Number of red passed  bytes."
        ::= { hwXQoSIfCarRunInfoEntry 16 }

    hwXQoSIfCarRedRemarkedPackets OBJECT-TYPE
        SYNTAX Counter64
        MAX-ACCESS read-only
        STATUS current
        DESCRIPTION
            "Number of red remarked packets."
        ::= { hwXQoSIfCarRunInfoEntry 17 }

    hwXQoSIfCarRedRemarkedBytes OBJECT-TYPE
        SYNTAX Counter64
        MAX-ACCESS read-only
        STATUS current
        DESCRIPTION
            "Number of red remarked bytes."
        ::= { hwXQoSIfCarRunInfoEntry 18 }

    hwXQoSIfCarRedDiscardedPackets OBJECT-TYPE
        SYNTAX Counter64
        MAX-ACCESS read-only
        STATUS current
        DESCRIPTION
            "Number of red discareded packets."
        ::= { hwXQoSIfCarRunInfoEntry 19 }

    hwXQoSIfCarRedDiscardedBytes OBJECT-TYPE
        SYNTAX Counter64
        MAX-ACCESS read-only
        STATUS current
        DESCRIPTION
            "Number of bytes exceeding CIR."
        ::= { hwXQoSIfCarRunInfoEntry 20 }

        -- 1.3.6.1.4.1.2011.5.25.32.4.1.4.3.1.1.21
        hwXQoSIfCarTotalDiscardPackets OBJECT-TYPE
            SYNTAX Counter64
            MAX-ACCESS read-only
            STATUS current
            DESCRIPTION
                "Number of total discard packets."
            ::= { hwXQoSIfCarRunInfoEntry 21 }

        -- 1.3.6.1.4.1.2011.5.25.32.4.1.4.3.1.1.22
        hwXQoSIfCarInBoundDiscardPackets OBJECT-TYPE
            SYNTAX Counter64
            MAX-ACCESS read-only
            STATUS current
            DESCRIPTION
                "Number of inbound direction discard packets."
            ::= { hwXQoSIfCarRunInfoEntry 22 }

        -- 1.3.6.1.4.1.2011.5.25.32.4.1.4.3.1.1.23
        hwXQoSIfCarOutBoundDiscardPackets OBJECT-TYPE
            SYNTAX Counter64
            MAX-ACCESS read-only
            STATUS current
            DESCRIPTION
                "Number of outbound direction discard packets."
            ::= { hwXQoSIfCarRunInfoEntry 23 }

--    Queue statistics
    hwXQoSIfQueueRunInfoTable OBJECT-TYPE
        SYNTAX SEQUENCE OF HwXQoSIfQueueRunInfoEntry
        MAX-ACCESS not-accessible
        STATUS current
        DESCRIPTION
            "This table is used to display the running information about an interface queue."
        ::= { hwXQoSIfStatisticsObjects 3 }

    hwXQoSIfQueueRunInfoEntry OBJECT-TYPE
        SYNTAX HwXQoSIfQueueRunInfoEntry
        MAX-ACCESS not-accessible
        STATUS current
        DESCRIPTION
            "Queue statistics entry."
        INDEX { hwXQoSIfQueueIfIndex, hwXQoSIfQueueVlanID, hwXQoSIfQueueCosType }
        ::= { hwXQoSIfQueueRunInfoTable 1 }

    HwXQoSIfQueueRunInfoEntry ::=
        SEQUENCE {
            hwXQoSIfQueueIfIndex
                Integer32,
            hwXQoSIfQueueVlanID
                Integer32,
            hwXQoSIfQueueCosType
                CosType,
            hwXQoSIfQueuePassedPackets
                Counter64,
            hwXQoSIfQueuePassededBytes
                Counter64,
            hwXQoSIfQueueTotalPackets
                Counter64,
            hwXQoSIfQueueTotalBytes
                Counter64,
            hwXQoSIfQueueDiscardedPackets
                Counter64,
            hwXQoSIfQueueDiscardedBytes
                Counter64,
            hwXQoSIfQueuePassedPacketRate
                Counter64,
            hwXQoSIfQueuePassedByteRate
                Counter64,
            hwXQoSIfQueueDiscardedPacketRate
                Counter64,
            hwXQoSIfQueueDiscardedByteRate
                Counter64,
            hwXQoSIfQueueResetFlag
                ResetFlag,
            hwXQoSIfQueueUsagePercentage
                Integer32,
            hwXQoSIfQueueDropTailDiscardedPackets
                Counter64,
            hwXQoSIfQueueDropTailDiscardedBytes
                Counter64,
            hwXQoSIfQueueWredDiscardedPackets
                Counter64,
            hwXQoSIfQueueWredDiscardedBytes
                Counter64,
            hwXQoSIfQueueDropTailDiscardedPacketRate
                Counter64,
            hwXQoSIfQueueDropTailDiscardedByteRate
                Counter64,
            hwXQoSIfQueueWredDiscardedPacketRate
                Counter64,
            hwXQoSIfQueueWredDiscardedByteRate
                Counter64,
            hwXQoSIfQueueStatisticsTrafficTowardThisPort
                    Counter64,
            hwXQoSIfQueueStatisticsPhysicalBandwidthOfPortQoS
                Counter64,
            hwXQoSIfQueuePassedPacketRate30s
                Counter64,
            hwXQoSIfQueuePassedBitsRate30s
                Counter64,
            hwXQoSIfQueueDiscardedPacketRate30s
                Counter64,
            hwXQoSIfQueueDiscardedBitsRate30s
                Counter64,
            hwXQoSIfQueuePassedPacketRate300s
                Counter64,
            hwXQoSIfQueuePassedBitsRate300s
                Counter64,
            hwXQoSIfQueueDiscardedPacketRate300s
                Counter64,
            hwXQoSIfQueueDiscardedBitsRate300s
                Counter64
         }

    hwXQoSIfQueueIfIndex OBJECT-TYPE
        SYNTAX Integer32
        MAX-ACCESS read-only
        STATUS current
        DESCRIPTION
            "The value of this object identifies the interface index."
        ::= { hwXQoSIfQueueRunInfoEntry 1 }

    hwXQoSIfQueueVlanID OBJECT-TYPE
        SYNTAX Integer32 (0 | 1..4095)
        MAX-ACCESS read-only
        STATUS current
        DESCRIPTION
            "This object indicates the VLAN ID."
        ::= { hwXQoSIfQueueRunInfoEntry 2 }

    hwXQoSIfQueueCosType OBJECT-TYPE
        SYNTAX CosType
        MAX-ACCESS read-only
        STATUS current
        DESCRIPTION
            "The value of this object identifies COS of the queue. The value can be any of the following: CS7(8), CS6(7), EF(6)
AF4(5),AF3(4),AF2(3),AF1(2),BE(1)."
        ::= { hwXQoSIfQueueRunInfoEntry 3 }

    hwXQoSIfQueuePassedPackets OBJECT-TYPE
        SYNTAX Counter64
        MAX-ACCESS read-only
        STATUS current
        DESCRIPTION
            "This object indicates the number of forwarded packets."
        ::= { hwXQoSIfQueueRunInfoEntry 4 }

    hwXQoSIfQueuePassededBytes OBJECT-TYPE
        SYNTAX Counter64
        MAX-ACCESS read-only
        STATUS current
        DESCRIPTION
            "This object indicates the number of bytes that pass the queue. The object has no default value."
        ::= { hwXQoSIfQueueRunInfoEntry 5 }

    hwXQoSIfQueueTotalPackets OBJECT-TYPE
        SYNTAX Counter64
        MAX-ACCESS read-only
        STATUS current
        DESCRIPTION
            "This object indicates the number of packets that reach the queue. The object has no default value."
        ::= { hwXQoSIfQueueRunInfoEntry 6 }

    hwXQoSIfQueueTotalBytes OBJECT-TYPE
        SYNTAX Counter64
        MAX-ACCESS read-only
        STATUS current
        DESCRIPTION
            "This object indicates the total number of bytes."
        ::= { hwXQoSIfQueueRunInfoEntry 7 }

    hwXQoSIfQueueDiscardedPackets OBJECT-TYPE
        SYNTAX Counter64
        MAX-ACCESS read-only
        STATUS current
        DESCRIPTION
            "This object indicates the number of discarded packets. "
        ::= { hwXQoSIfQueueRunInfoEntry 8 }

    hwXQoSIfQueueDiscardedBytes OBJECT-TYPE
        SYNTAX Counter64
        MAX-ACCESS read-only
        STATUS current
        DESCRIPTION
            "This object indicates the number of discarded bytes. "
        ::= { hwXQoSIfQueueRunInfoEntry 9 }

    hwXQoSIfQueuePassedPacketRate OBJECT-TYPE
        SYNTAX Counter64
        MAX-ACCESS read-only
        STATUS current
        DESCRIPTION
            "This object indicates the rate at which packets are forwarded."
        ::= { hwXQoSIfQueueRunInfoEntry 10 }

    hwXQoSIfQueuePassedByteRate OBJECT-TYPE
        SYNTAX Counter64
        MAX-ACCESS read-only
        STATUS current
        DESCRIPTION
            "This object indicates the rate at which bytes are forwarded. "
        ::= { hwXQoSIfQueueRunInfoEntry 11 }

    hwXQoSIfQueueDiscardedPacketRate OBJECT-TYPE
        SYNTAX Counter64
        MAX-ACCESS read-only
        STATUS current
        DESCRIPTION
            "This object indicates the packet rate of discarded packets, in pps. The object has no default value."
        ::= { hwXQoSIfQueueRunInfoEntry 12 }

    hwXQoSIfQueueDiscardedByteRate OBJECT-TYPE
        SYNTAX Counter64
        MAX-ACCESS read-only
        STATUS current
        DESCRIPTION
            "This object indicates the rate at which bytes are discarded. "
        ::= { hwXQoSIfQueueRunInfoEntry 13 }

     hwXQoSIfQueueResetFlag OBJECT-TYPE
        SYNTAX ResetFlag
        MAX-ACCESS read-write
        STATUS current
        DESCRIPTION
            "Reset queue statistics information."
        ::= { hwXQoSIfQueueRunInfoEntry 14 }

     hwXQoSIfQueueUsagePercentage OBJECT-TYPE
        SYNTAX Integer32
        MAX-ACCESS read-only
        STATUS current
        DESCRIPTION
            "This object indicates the percentage of the queue usage. "
        ::= { hwXQoSIfQueueRunInfoEntry 15 }

      hwXQoSIfQueueDropTailDiscardedPackets OBJECT-TYPE
            SYNTAX  Counter64
            MAX-ACCESS read-only
            STATUS current
            DESCRIPTION
            " The value of this object identifies the number of discarded tail packets. "
            ::= { hwXQoSIfQueueRunInfoEntry 16 }

      hwXQoSIfQueueDropTailDiscardedBytes OBJECT-TYPE
            SYNTAX  Counter64
            MAX-ACCESS read-only
            STATUS current
            DESCRIPTION
            " This object indicates the number of bytes discarded by tail drop. "
            ::= { hwXQoSIfQueueRunInfoEntry 17 }

      hwXQoSIfQueueWredDiscardedPackets OBJECT-TYPE
            SYNTAX  Counter64
            MAX-ACCESS read-only
            STATUS current
            DESCRIPTION
            " The value of this object identifies the number of packets that are discarded by WRED. "
            ::= { hwXQoSIfQueueRunInfoEntry 18 }

      hwXQoSIfQueueWredDiscardedBytes OBJECT-TYPE
            SYNTAX  Counter64
            MAX-ACCESS read-only
            STATUS current
            DESCRIPTION
            "This object indicates the number of bytes discarded by WRED. "
            ::= { hwXQoSIfQueueRunInfoEntry 19 }

      hwXQoSIfQueueDropTailDiscardedPacketRate OBJECT-TYPE
            SYNTAX  Counter64
            MAX-ACCESS read-only
            STATUS current
            DESCRIPTION
            " This object indicates the tail packet discarding rate. "
            ::= { hwXQoSIfQueueRunInfoEntry 20 }

      hwXQoSIfQueueDropTailDiscardedByteRate OBJECT-TYPE
            SYNTAX  Counter64
            MAX-ACCESS read-only
            STATUS current
            DESCRIPTION
            "This object indicates the rate at which packets are discarded by tail drop. "
            ::= { hwXQoSIfQueueRunInfoEntry 21 }

      hwXQoSIfQueueWredDiscardedPacketRate OBJECT-TYPE
            SYNTAX  Counter64
            MAX-ACCESS read-only
            STATUS current
            DESCRIPTION
            " This object indicates the WRED packet discarding rate."
            ::= { hwXQoSIfQueueRunInfoEntry 22 }

      hwXQoSIfQueueWredDiscardedByteRate OBJECT-TYPE
            SYNTAX  Counter64
            MAX-ACCESS read-only
            STATUS current
            DESCRIPTION
            " This object indicates the rate at which packets are discarded by WRED."
            ::= { hwXQoSIfQueueRunInfoEntry 23 }

      hwXQoSIfQueueStatisticsTrafficTowardThisPort OBJECT-TYPE
            SYNTAX  Counter64
            MAX-ACCESS read-only
            STATUS current
            DESCRIPTION
            " This object indicates the traffic which towards this port."
            ::= { hwXQoSIfQueueRunInfoEntry 24 }

      hwXQoSIfQueueStatisticsPhysicalBandwidthOfPortQoS OBJECT-TYPE
            SYNTAX  Counter64
            MAX-ACCESS read-only
            STATUS current
            DESCRIPTION
            " This object indicates the physical bandwidth of a QoS interface."
            ::= { hwXQoSIfQueueRunInfoEntry 25 }

    hwXQoSIfQueuePassedPacketRate30s OBJECT-TYPE
        SYNTAX Counter64
        MAX-ACCESS read-only
        STATUS current
        DESCRIPTION
            "This object indicates the last 30 seconds packet rate, in pps.The object has no default value."
        ::= { hwXQoSIfQueueRunInfoEntry 26 }

    hwXQoSIfQueuePassedBitsRate30s OBJECT-TYPE
        SYNTAX Counter64
        MAX-ACCESS read-only
        STATUS current
        DESCRIPTION
            "This object indicates the last 30 seconds bit rate, in bps.The object has no default value."
        ::= { hwXQoSIfQueueRunInfoEntry 27 }

    hwXQoSIfQueueDiscardedPacketRate30s OBJECT-TYPE
        SYNTAX Counter64
        MAX-ACCESS read-only
        STATUS current
        DESCRIPTION
            "This object indicates the last 30 seconds packet rate of discarded packets, in pps.The object has no default value."
        ::= { hwXQoSIfQueueRunInfoEntry 28 }

    hwXQoSIfQueueDiscardedBitsRate30s OBJECT-TYPE
        SYNTAX Counter64
        MAX-ACCESS read-only
        STATUS current
        DESCRIPTION
            "This object indicates the last 30 seconds bit rate of discarded packets, in bps.The object has no default value."
        ::= { hwXQoSIfQueueRunInfoEntry 29 }
    hwXQoSIfQueuePassedPacketRate300s OBJECT-TYPE
        SYNTAX Counter64
        MAX-ACCESS read-only
        STATUS current
        DESCRIPTION
            "This object indicates the last 300 seconds packet rate, in pps.The object has no default value."
        ::= { hwXQoSIfQueueRunInfoEntry 30 }

    hwXQoSIfQueuePassedBitsRate300s OBJECT-TYPE
        SYNTAX Counter64
        MAX-ACCESS read-only
        STATUS current
        DESCRIPTION
            "This object indicates the last 300 seconds bit rate, in bps.The object has no default value."
        ::= { hwXQoSIfQueueRunInfoEntry 31 }

    hwXQoSIfQueueDiscardedPacketRate300s OBJECT-TYPE
        SYNTAX Counter64
        MAX-ACCESS read-only
        STATUS current
        DESCRIPTION
            "This object indicates the last 300 seconds packet rate of discarded packets, in pps.The object has no default value."
        ::= { hwXQoSIfQueueRunInfoEntry 32 }

    hwXQoSIfQueueDiscardedBitsRate300s OBJECT-TYPE
        SYNTAX Counter64
        MAX-ACCESS read-only
        STATUS current
        DESCRIPTION
            "This object indicates the last 300 seconds bit rate of discarded packets, in bps.The object has no default value."
        ::= { hwXQoSIfQueueRunInfoEntry 33 }
--    WRED statistics
    hwXQoSIfWredRunInfoTable OBJECT-TYPE
        SYNTAX SEQUENCE OF HwXQoSIfWredRunInfoEntry
        MAX-ACCESS not-accessible
        STATUS current
        DESCRIPTION
            "A table of Running statistics for WRED
            in a QoS policy applied on the interface."
        ::= { hwXQoSIfStatisticsObjects 4 }

    hwXQoSIfWredRunInfoEntry OBJECT-TYPE
        SYNTAX HwXQoSIfWredRunInfoEntry
        MAX-ACCESS not-accessible
        STATUS current
        DESCRIPTION
            "WRED statistics entry."
        INDEX { hwXQoSIfWredIfIndex, hwXQoSIfWredVlanID }
        ::= { hwXQoSIfWredRunInfoTable 1 }

    HwXQoSIfWredRunInfoEntry ::=
        SEQUENCE {
            hwXQoSIfWredIfIndex
                Integer32,
            hwXQoSIfWredVlanID
                Integer32,
            hwXQoSIfWredRandomDiscardedPackets
                Counter64,
            hwXQoSIfWredTailDiscardedPackets
                Counter64,
            hwXQoSIfWredDiscardedPackets
                Counter64
         }

    hwXQoSIfWredIfIndex OBJECT-TYPE
        SYNTAX Integer32
        MAX-ACCESS read-only
        STATUS current
        DESCRIPTION
            "Index of interface."
        ::= { hwXQoSIfWredRunInfoEntry 1 }

    hwXQoSIfWredVlanID OBJECT-TYPE
        SYNTAX Integer32 (0 | 1..4095)
        MAX-ACCESS read-only
        STATUS current
        DESCRIPTION
            "Vlan ID.
            -1 can't be set.
            0 is the default value"
        ::= { hwXQoSIfWredRunInfoEntry 2 }

    hwXQoSIfWredRandomDiscardedPackets OBJECT-TYPE
        SYNTAX Counter64
        MAX-ACCESS read-only
        STATUS current
        DESCRIPTION
            "Number of packets that random-discarded by WRED."
        ::= { hwXQoSIfWredRunInfoEntry 3 }


    hwXQoSIfWredTailDiscardedPackets OBJECT-TYPE
        SYNTAX Counter64
        MAX-ACCESS read-only
        STATUS current
        DESCRIPTION
            "Number of packets that tail-discarded by WRED."
        ::= { hwXQoSIfWredRunInfoEntry 4 }

    hwXQoSIfWredDiscardedPackets OBJECT-TYPE
        SYNTAX Counter64
        MAX-ACCESS read-only
        STATUS current
        DESCRIPTION
            "Number of packets that discarded by WRED.
            Include random-discarded and tail-discarded"
        ::= { hwXQoSIfWredRunInfoEntry 5 }

--    LR statistics
    hwXQoSIfLrRunInfoTable OBJECT-TYPE
        SYNTAX SEQUENCE OF HwXQoSIfLrRunInfoEntry
        MAX-ACCESS not-accessible
        STATUS current
        DESCRIPTION
            "A table of Running statistics for LR
            in a QoS policy applied on the interface."
        ::= { hwXQoSIfStatisticsObjects 5 }

    hwXQoSIfLrRunInfoEntry OBJECT-TYPE
        SYNTAX HwXQoSIfLrRunInfoEntry
        MAX-ACCESS not-accessible
        STATUS current
        DESCRIPTION
            "LR statistics entry."
        INDEX { hwXQoSIfLrIfIndex, hwXQoSIfLrVlanID }
        ::= { hwXQoSIfLrRunInfoTable 1 }

    HwXQoSIfLrRunInfoEntry ::=
        SEQUENCE {
            hwXQoSIfLrIfIndex
                Integer32,
            hwXQoSIfLrVlanID
                Integer32,
            hwXQoSIfLrPassedPackets
                Counter64,
            hwXQoSIfLrPassedBytes
                Counter64,
            hwXQoSIfLrDiscardedPackets
                Counter64,
            hwXQoSIfLrDiscardedBytes
                Counter64,
            hwXQoSIfLrDelayedPackets
                Counter64,
            hwXQoSIfLrDelayedBytes
                Counter64
         }

    hwXQoSIfLrIfIndex OBJECT-TYPE
        SYNTAX Integer32
        MAX-ACCESS read-only
        STATUS current
        DESCRIPTION
            "Index of Interface of LR."
        ::= { hwXQoSIfLrRunInfoEntry 1 }

    hwXQoSIfLrVlanID OBJECT-TYPE
        SYNTAX Integer32 (0 | 1..4095)
        MAX-ACCESS read-only
        STATUS current
        DESCRIPTION
            "Vlan ID.
            -1 can't be set.
            0 is the default value"
        ::= { hwXQoSIfLrRunInfoEntry 2 }

    hwXQoSIfLrPassedPackets OBJECT-TYPE
        SYNTAX Counter64
        MAX-ACCESS read-only
        STATUS current
        DESCRIPTION
            "Number of packets passed by LR."
        ::= { hwXQoSIfLrRunInfoEntry 3 }

    hwXQoSIfLrPassedBytes OBJECT-TYPE
        SYNTAX Counter64
        MAX-ACCESS read-only
        STATUS current
        DESCRIPTION
            "Number of bytes passed by LR."
        ::= { hwXQoSIfLrRunInfoEntry 4 }

    hwXQoSIfLrDiscardedPackets OBJECT-TYPE
        SYNTAX Counter64
        MAX-ACCESS read-only
        STATUS current
        DESCRIPTION
            "Number of packets discarded by LR."
        ::= { hwXQoSIfLrRunInfoEntry 5 }

    hwXQoSIfLrDiscardedBytes OBJECT-TYPE
        SYNTAX Counter64
        MAX-ACCESS read-only
        STATUS current
        DESCRIPTION
            "Number of bytes discarded by LR."
        ::= { hwXQoSIfLrRunInfoEntry 6 }

    hwXQoSIfLrDelayedPackets OBJECT-TYPE
        SYNTAX Counter64
        MAX-ACCESS read-only
        STATUS current
        DESCRIPTION
            "Number of packets delayed by LR."
        ::= { hwXQoSIfLrRunInfoEntry 7 }

    hwXQoSIfLrDelayedBytes OBJECT-TYPE
        SYNTAX Counter64
        MAX-ACCESS read-only
        STATUS current
        DESCRIPTION
            "Number of bytes delayed by LR."
        ::= { hwXQoSIfLrRunInfoEntry 8 }

--    Mirror statistics
    hwXQoSIfMirrorRunInfoTable OBJECT-TYPE
        SYNTAX SEQUENCE OF HwXQoSIfMirrorRunInfoEntry
        MAX-ACCESS not-accessible
        STATUS current
        DESCRIPTION
            "A table of Running statistics for mirror
            in a QoS policy applied on the interface."
        ::= { hwXQoSIfStatisticsObjects 6 }

    hwXQoSIfMirrorRunInfoEntry OBJECT-TYPE
        SYNTAX HwXQoSIfMirrorRunInfoEntry
        MAX-ACCESS not-accessible
        STATUS current
        DESCRIPTION
            "Mirror statistics entry."
        INDEX { hwXQoSIfMirrorIfIndex, hwXQoSIfMirrorVlanID }
        ::= { hwXQoSIfMirrorRunInfoTable 1 }

    HwXQoSIfMirrorRunInfoEntry ::=
        SEQUENCE {
            hwXQoSIfMirrorIfIndex
                Integer32,
            hwXQoSIfMirrorVlanID
                Integer32,
            hwXQoSIfMirroredPackets
                Counter64
         }

    hwXQoSIfMirrorIfIndex OBJECT-TYPE
        SYNTAX Integer32
        MAX-ACCESS read-only
        STATUS current
        DESCRIPTION
            "Index of interface mirror."
        ::= { hwXQoSIfMirrorRunInfoEntry 1 }

    hwXQoSIfMirrorVlanID OBJECT-TYPE
        SYNTAX Integer32 (0 | 1..4095)
        MAX-ACCESS read-only
        STATUS current
        DESCRIPTION
            "Vlan ID.
            -1 can't be set.
            0 is the default value"
        ::= { hwXQoSIfMirrorRunInfoEntry 2 }

    hwXQoSIfMirroredPackets OBJECT-TYPE
        SYNTAX Counter64
        MAX-ACCESS read-only
        STATUS current
        DESCRIPTION
            "Number of packets Mirrored."
        ::= { hwXQoSIfMirrorRunInfoEntry 3 }

--    Urpf statistics
    hwXQoSIfUrpfRunInfoTable OBJECT-TYPE
        SYNTAX SEQUENCE OF HwXQoSIfUrpfRunInfoEntry
        MAX-ACCESS not-accessible
        STATUS current
        DESCRIPTION
            "A table of Running statistics for urpf
            in a QoS policy applied on the interface."
        ::= { hwXQoSIfStatisticsObjects 7 }


    hwXQoSIfUrpfRunInfoEntry OBJECT-TYPE
        SYNTAX HwXQoSIfUrpfRunInfoEntry
        MAX-ACCESS not-accessible
        STATUS current
        DESCRIPTION
            "Urpf statistics entry."
        INDEX { hwXQoSIfUrpfIfIndex, hwXQoSIfUrpfVlanID }
        ::= { hwXQoSIfUrpfRunInfoTable 1 }

    HwXQoSIfUrpfRunInfoEntry ::=
        SEQUENCE {
            hwXQoSIfUrpfIfIndex
                Integer32,
            hwXQoSIfUrpfVlanID
                Integer32,
            hwXQoSIfUrpfPassedPackets
                Counter64,
            hwXQoSIfUrpfDroppdPackets
                Counter64
         }

    hwXQoSIfUrpfIfIndex OBJECT-TYPE
        SYNTAX Integer32
        MAX-ACCESS read-only
        STATUS current
        DESCRIPTION
            "Index of interface URPF."
        ::= { hwXQoSIfUrpfRunInfoEntry 1 }

    hwXQoSIfUrpfVlanID OBJECT-TYPE
        SYNTAX Integer32 (0 | 1..4095)
        MAX-ACCESS read-only
        STATUS current
        DESCRIPTION
            "Vlan ID.
            -1 can't be set.
            0 is the default value"
        ::= { hwXQoSIfUrpfRunInfoEntry 2 }

    hwXQoSIfUrpfPassedPackets OBJECT-TYPE
        SYNTAX Counter64
        MAX-ACCESS read-only
        STATUS current
        DESCRIPTION
            "Number of packets passed."
        ::= { hwXQoSIfUrpfRunInfoEntry 3 }

    hwXQoSIfUrpfDroppdPackets OBJECT-TYPE
        SYNTAX Counter64
        MAX-ACCESS read-only
        STATUS current
        DESCRIPTION
            "Number of packets dropped."
        ::= { hwXQoSIfUrpfRunInfoEntry 4 }

--    Sample statistics
    hwXQoSIfSampleRunInfoTable OBJECT-TYPE
        SYNTAX SEQUENCE OF HwXQoSIfSampleRunInfoEntry
        MAX-ACCESS not-accessible
        STATUS current
        DESCRIPTION
            "A table of Running statistics for sample
            in a QoS policy applied on the interface."
        ::= { hwXQoSIfStatisticsObjects 8 }

    hwXQoSIfSampleRunInfoEntry OBJECT-TYPE
        SYNTAX HwXQoSIfSampleRunInfoEntry
        MAX-ACCESS not-accessible
        STATUS current
        DESCRIPTION
            "Sample statistics entry."
        INDEX { hwXQoSIfSampleIfIndex, hwXQoSIfSampleVlanID }
        ::= { hwXQoSIfSampleRunInfoTable 1 }

    HwXQoSIfSampleRunInfoEntry ::=
        SEQUENCE {
            hwXQoSIfSampleIfIndex
                Integer32,
            hwXQoSIfSampleVlanID
                Integer32,
            hwXQoSIfSampledPackets
                Counter64
         }

    hwXQoSIfSampleIfIndex OBJECT-TYPE
        SYNTAX Integer32
        MAX-ACCESS read-only
        STATUS current
        DESCRIPTION
            "Index of interface Sample."
        ::= { hwXQoSIfSampleRunInfoEntry 1 }

    hwXQoSIfSampleVlanID OBJECT-TYPE
        SYNTAX Integer32 (0 | 1..4095)
        MAX-ACCESS read-only
        STATUS current
        DESCRIPTION
            "Vlan ID.
            -1 can't be set.
            0 is the default value"
        ::= { hwXQoSIfSampleRunInfoEntry 2 }

    hwXQoSIfSampledPackets OBJECT-TYPE
        SYNTAX Counter64
        MAX-ACCESS read-only
        STATUS current
        DESCRIPTION
            "Number of packets Sampled."
        ::= { hwXQoSIfSampleRunInfoEntry 3 }

-- CAR statistics
    hwXQoSIfCarStatisticsTable OBJECT-TYPE
        SYNTAX SEQUENCE OF HwXQoSIfCarStatisticsEntry
        MAX-ACCESS not-accessible
        STATUS current
        DESCRIPTION
            "This table is used to display the CAR statistics of a port."
        ::= { hwXQoSIfStatisticsObjects 9 }

    hwXQoSIfCarStatisticsEntry OBJECT-TYPE
        SYNTAX HwXQoSIfCarStatisticsEntry
        MAX-ACCESS not-accessible
        STATUS current
        DESCRIPTION
            "A table of CAR statistics for port-based traffic, including
            the statistics of  packets that have the rate within CIR, of
            CIR, of PIR or exceeds PIR. ."
        INDEX { hwXQoSIfCarCfgIfIndex, hwXQoSIfCarVlanID,
            hwXQoSIfCarDirection }
        ::= { hwXQoSIfCarStatisticsTable 1 }

    HwXQoSIfCarStatisticsEntry ::=
        SEQUENCE {
            hwXQoSIfCarConformedPackets
                Counter64,
            hwXQoSIfCarConformedBytes
                Counter64,
            hwXQoSIfCarConformedPacketRate
                Counter64,
            hwXQoSIfCarConformedByteRate
                Counter64,
            hwXQoSIfCarExceededPackets
                Counter64,
            hwXQoSIfCarExceededBytes
                Counter64,
            hwXQoSIfCarExceededPacketRate
                Counter64,
            hwXQoSIfCarExceededByteRate
                Counter64,
            hwXQoSIfCarOverflowPackets
                Counter64,
            hwXQoSIfCarOverflowBytes
                Counter64,
            hwXQoSIfCarOverflowPacketRate
                Counter64,
            hwXQoSIfCarOverflowByteRate
                Counter64,
            hwXQoSIfCarPassedPackets
                Counter64,
            hwXQoSIfCarPassedBytes
                Counter64,
            hwXQoSIfCarDiscardedPackets
                Counter64,
            hwXQoSIfCarDiscardedBytes
                Counter64
         }

    hwXQoSIfCarConformedPackets OBJECT-TYPE
        SYNTAX Counter64
        MAX-ACCESS read-only
        STATUS current
        DESCRIPTION
            "This object indicates the number of green packets for the interface CAR."
        ::= { hwXQoSIfCarStatisticsEntry 11 }

    hwXQoSIfCarConformedBytes OBJECT-TYPE
        SYNTAX Counter64
        MAX-ACCESS read-only
        STATUS current
        DESCRIPTION
            "This object indicates the number of bytes within CIR."
        ::= { hwXQoSIfCarStatisticsEntry 12 }

    hwXQoSIfCarConformedPacketRate OBJECT-TYPE
        SYNTAX Counter64
        MAX-ACCESS read-only
        STATUS current
        DESCRIPTION
            "This object indicates the rate of green packets for the interface CAR, in pps."
        ::= { hwXQoSIfCarStatisticsEntry 13 }

    hwXQoSIfCarConformedByteRate OBJECT-TYPE
        SYNTAX Counter64
        MAX-ACCESS read-only
        STATUS current
        DESCRIPTION
            "This object indicates the byte rate within CIR, in bps."
        ::= { hwXQoSIfCarStatisticsEntry 14 }

    hwXQoSIfCarExceededPackets OBJECT-TYPE
        SYNTAX Counter64
        MAX-ACCESS read-only
        STATUS current
        DESCRIPTION
            "This object indicates the number of yellow packets for the interface CAR."
        ::= { hwXQoSIfCarStatisticsEntry 15 }

    hwXQoSIfCarExceededBytes OBJECT-TYPE
        SYNTAX Counter64
        MAX-ACCESS read-only
        STATUS current
        DESCRIPTION
            "This object indicates the number of bytes between PIR and CIR."
        ::= { hwXQoSIfCarStatisticsEntry 16 }

    hwXQoSIfCarExceededPacketRate OBJECT-TYPE
        SYNTAX Counter64
        MAX-ACCESS read-only
        STATUS current
        DESCRIPTION
            "This object indicates the packet rate between PIR and CIR, in pps."
        ::= { hwXQoSIfCarStatisticsEntry 17 }

    hwXQoSIfCarExceededByteRate OBJECT-TYPE
        SYNTAX Counter64
        MAX-ACCESS read-only
        STATUS current
        DESCRIPTION
            "This object indicates the rate of yellow bytes for the interface CAR, in pps."
        ::= { hwXQoSIfCarStatisticsEntry 18 }

    hwXQoSIfCarOverflowPackets OBJECT-TYPE
        SYNTAX Counter64
        MAX-ACCESS read-only
        STATUS current
        DESCRIPTION
            "This object indicates the number of red packets for the interface CAR."
        ::= { hwXQoSIfCarStatisticsEntry 19 }

    hwXQoSIfCarOverflowBytes OBJECT-TYPE
        SYNTAX Counter64
        MAX-ACCESS read-only
        STATUS current
        DESCRIPTION
            "This object indicates the number of red bytes for the interface CAR."
        ::= { hwXQoSIfCarStatisticsEntry 20 }

    hwXQoSIfCarOverflowPacketRate OBJECT-TYPE
        SYNTAX Counter64
        MAX-ACCESS read-only
        STATUS current
        DESCRIPTION
            "This object indicates the rate of red packets for the interface CAR."
        ::= { hwXQoSIfCarStatisticsEntry 21 }

    hwXQoSIfCarOverflowByteRate OBJECT-TYPE
        SYNTAX Counter64
        MAX-ACCESS read-only
        STATUS current
        DESCRIPTION
            "This object indicates the rate of red bytes for the interface CAR."
        ::= { hwXQoSIfCarStatisticsEntry 22 }

    hwXQoSIfCarPassedPackets OBJECT-TYPE
        SYNTAX Counter64
        MAX-ACCESS read-only
        STATUS current
        DESCRIPTION
            "This object indicates the number of forwarded packets after CAR is applied."
        ::= { hwXQoSIfCarStatisticsEntry 23 }

    hwXQoSIfCarPassedBytes OBJECT-TYPE
        SYNTAX Counter64
        MAX-ACCESS read-only
        STATUS current
        DESCRIPTION
            "This object indicates the number of forwarded bytes after CAR is applied."
        ::= { hwXQoSIfCarStatisticsEntry 24 }

    hwXQoSIfCarDiscardedPackets OBJECT-TYPE
        SYNTAX Counter64
        MAX-ACCESS read-only
        STATUS current
        DESCRIPTION
            "This object indicates the number of discarded packets after CAR is set."
        ::= { hwXQoSIfCarStatisticsEntry 25 }

    hwXQoSIfCarDiscardedBytes OBJECT-TYPE
        SYNTAX Counter64
        MAX-ACCESS read-only
        STATUS current
        DESCRIPTION
            "This object indicates the number of discarded bytes after CAR is applied."
        ::= { hwXQoSIfCarStatisticsEntry 26 }

    hwXQoSIfOutboundQueueStatisticTable OBJECT-TYPE
        SYNTAX SEQUENCE OF HwXQoSIfOutboundQueueStatisticEntry
        MAX-ACCESS not-accessible
        STATUS current
        DESCRIPTION
            "The table provides the discard packets."
        ::= { hwXQoSIfStatisticsObjects 10 }

    hwXQoSIfOutboundQueueStatisticEntry OBJECT-TYPE
        SYNTAX HwXQoSIfOutboundQueueStatisticEntry
        MAX-ACCESS not-accessible
        STATUS current
        DESCRIPTION
            "The discard packets entry."
        INDEX { hwXQoSIfExtIndex, hwXQoSIfQueIndex }
        ::= { hwXQoSIfOutboundQueueStatisticTable 1 }

    HwXQoSIfOutboundQueueStatisticEntry ::=
        SEQUENCE {
            hwXQoSIfExtIndex
                Unsigned32,
            hwXQoSIfQueIndex
                OCTET STRING,
            hwXQoSIfQueDiscardPackets
                Integer32
        }

    hwXQoSIfExtIndex OBJECT-TYPE
        SYNTAX Unsigned32
        MAX-ACCESS not-accessible
        STATUS current
        DESCRIPTION
            "Index for the extended interface."
        ::= { hwXQoSIfOutboundQueueStatisticEntry 1 }

    hwXQoSIfQueIndex OBJECT-TYPE
        SYNTAX OCTET STRING
        MAX-ACCESS not-accessible
        STATUS current
        DESCRIPTION
            "Index for the queue."
        ::= { hwXQoSIfOutboundQueueStatisticEntry 2 }

    hwXQoSIfQueDiscardPackets OBJECT-TYPE
        SYNTAX Integer32
        MAX-ACCESS read-only
        STATUS current
        DESCRIPTION
            "Number of discarded packets."
        ::= { hwXQoSIfOutboundQueueStatisticEntry 3 }

--hwXQoSIfCarStatisticsExtTable
    hwXQoSIfCarStatisticsExtTable OBJECT-TYPE
        SYNTAX SEQUENCE OF HwXQoSIfCarStatisticsExtEntry
        MAX-ACCESS not-accessible
        STATUS current
        DESCRIPTION
            "This table is used to display the CAR statistics of a port."
        ::= { hwXQoSIfStatisticsObjects 11 }

    hwXQoSIfCarStatisticsExtEntry OBJECT-TYPE
        SYNTAX HwXQoSIfCarStatisticsExtEntry
        MAX-ACCESS not-accessible
        STATUS current
        DESCRIPTION
            "A table of CAR statistics for port-based traffic, including
            the statistics of  packets that have the rate within CIR, of
            CIR, of PIR or exceeds PIR. ."
        INDEX { hwXQoSIfCarCfgIfIndex, hwXQoSIfCarVlanID,
            hwXQoSIfCarDirection }
        ::= { hwXQoSIfCarStatisticsExtTable 1 }

    HwXQoSIfCarStatisticsExtEntry ::=
        SEQUENCE {
            hwXQoSIfCarExtConformedPacketsLow
                Unsigned32,
            hwXQoSIfCarExtConformedPacketsHigh
                Unsigned32,
            hwXQoSIfCarExtConformedBytesLow
                Unsigned32,
            hwXQoSIfCarExtConformedBytesHigh
                Unsigned32,
            hwXQoSIfCarExtConformedPacketRateLow
                Unsigned32,
            hwXQoSIfCarExtConformedPacketRateHigh
                Unsigned32,
            hwXQoSIfCarExtConformedByteRateLow
                Unsigned32,
            hwXQoSIfCarExtConformedByteRateHigh
                Unsigned32,
            hwXQoSIfCarExtExceededPacketsLow
                Unsigned32,
            hwXQoSIfCarExtExceededPacketsHigh
                Unsigned32,
            hwXQoSIfCarExtExceededBytesLow
                Unsigned32,
            hwXQoSIfCarExtExceededBytesHigh
                Unsigned32,
            hwXQoSIfCarExtExceededPacketRateLow
                Unsigned32,
            hwXQoSIfCarExtExceededPacketRateHigh
                Unsigned32,
            hwXQoSIfCarExtExceededByteRateLow
                Unsigned32,
            hwXQoSIfCarExtExceededByteRateHigh
                Unsigned32,
            hwXQoSIfCarExtOverflowPacketsLow
                Unsigned32,
            hwXQoSIfCarExtOverflowPacketsHigh
                Unsigned32,
            hwXQoSIfCarExtOverflowBytesLow
                Unsigned32,
            hwXQoSIfCarExtOverflowBytesHigh
                Unsigned32,
            hwXQoSIfCarExtOverflowPacketRateLow
                Unsigned32,
            hwXQoSIfCarExtOverflowPacketRateHigh
                Unsigned32,
            hwXQoSIfExtCarOverflowByteRateLow
                Unsigned32,
            hwXQoSIfExtCarOverflowByteRateHigh
                Unsigned32,
            hwXQoSIfCarExtPassedPacketsLow
                Unsigned32,
            hwXQoSIfCarExtPassedPacketsHigh
                Unsigned32,
            hwXQoSIfCarExtPassedBytesLow
                Unsigned32,
            hwXQoSIfCarExtPassedBytesHigh
                Unsigned32,
            hwXQoSIfCarExtDiscardedPacketsLow
                Unsigned32,
            hwXQoSIfCarExtDiscardedPacketsHigh
                Unsigned32,
            hwXQoSIfCarExtDiscardedBytesLow
                Unsigned32,
            hwXQoSIfCarExtDiscardedBytesHigh
                Unsigned32
         }

    hwXQoSIfCarExtConformedPacketsLow OBJECT-TYPE
        SYNTAX Unsigned32
        MAX-ACCESS read-only
        STATUS current
        DESCRIPTION
            "This object indicates the number of green packets for the interface CAR, which is lower 32 bits of the total number."
        ::= { hwXQoSIfCarStatisticsExtEntry 11 }

    hwXQoSIfCarExtConformedPacketsHigh OBJECT-TYPE
        SYNTAX Unsigned32
        MAX-ACCESS read-only
        STATUS current
        DESCRIPTION
            "This object indicates the number of green packets for the interface CAR, which is upper 32 bits of the total number."
        ::= { hwXQoSIfCarStatisticsExtEntry 12 }

    hwXQoSIfCarExtConformedBytesLow OBJECT-TYPE
        SYNTAX Unsigned32
        MAX-ACCESS read-only
        STATUS current
        DESCRIPTION
            "This object indicates the number of bytes within CIR, which is lower 32 bits of the total number."
        ::= { hwXQoSIfCarStatisticsExtEntry 13 }

    hwXQoSIfCarExtConformedBytesHigh OBJECT-TYPE
        SYNTAX Unsigned32
        MAX-ACCESS read-only
        STATUS current
        DESCRIPTION
            "This object indicates the number of bytes within CIR, which is upper 32 bits of the total number."
        ::= { hwXQoSIfCarStatisticsExtEntry 14 }

    hwXQoSIfCarExtConformedPacketRateLow OBJECT-TYPE
        SYNTAX Unsigned32
        MAX-ACCESS read-only
        STATUS current
        DESCRIPTION
            "This object indicates the rate of green packets for the interface CAR, in pps, which is lower 32 bits of the total number."
        ::= { hwXQoSIfCarStatisticsExtEntry 15 }

    hwXQoSIfCarExtConformedPacketRateHigh OBJECT-TYPE
        SYNTAX Unsigned32
        MAX-ACCESS read-only
        STATUS current
        DESCRIPTION
            "This object indicates the rate of green packets for the interface CAR, in pps, which is upper 32 bits of the total number."
        ::= { hwXQoSIfCarStatisticsExtEntry 16 }

    hwXQoSIfCarExtConformedByteRateLow OBJECT-TYPE
        SYNTAX Unsigned32
        MAX-ACCESS read-only
        STATUS current
        DESCRIPTION
            "This object indicates the byte rate within CIR, in bps, which is lower 32 bits of the total number."
        ::= { hwXQoSIfCarStatisticsExtEntry 17 }

    hwXQoSIfCarExtConformedByteRateHigh OBJECT-TYPE
        SYNTAX Unsigned32
        MAX-ACCESS read-only
        STATUS current
        DESCRIPTION
            "This object indicates the byte rate within CIR, in bps, which is upper 32 bits of the total number."
        ::= { hwXQoSIfCarStatisticsExtEntry 18 }

    hwXQoSIfCarExtExceededPacketsLow OBJECT-TYPE
        SYNTAX Unsigned32
        MAX-ACCESS read-only
        STATUS current
        DESCRIPTION
            "This object indicates the number of yellow packets for the interface CAR, which is lower 32 bits of the total number."
        ::= { hwXQoSIfCarStatisticsExtEntry 19 }

    hwXQoSIfCarExtExceededPacketsHigh OBJECT-TYPE
        SYNTAX Unsigned32
        MAX-ACCESS read-only
        STATUS current
        DESCRIPTION
            "This object indicates the number of yellow packets for the interface CAR, which is upper 32 bits of the total number."
        ::= { hwXQoSIfCarStatisticsExtEntry 20 }

    hwXQoSIfCarExtExceededBytesLow OBJECT-TYPE
        SYNTAX Unsigned32
        MAX-ACCESS read-only
        STATUS current
        DESCRIPTION
            "This object indicates the number of bytes between PIR and CIR, which is lower 32 bits of the total number."
        ::= { hwXQoSIfCarStatisticsExtEntry 21 }

    hwXQoSIfCarExtExceededBytesHigh OBJECT-TYPE
        SYNTAX Unsigned32
        MAX-ACCESS read-only
        STATUS current
        DESCRIPTION
            "This object indicates the number of bytes between PIR and CIR, which is upper 32 bits of the total number."
        ::= { hwXQoSIfCarStatisticsExtEntry 22 }

    hwXQoSIfCarExtExceededPacketRateLow OBJECT-TYPE
        SYNTAX Unsigned32
        MAX-ACCESS read-only
        STATUS current
        DESCRIPTION
            "This object indicates the packet rate between PIR and CIR, in pps, which is lower 32 bits of the total number."
        ::= { hwXQoSIfCarStatisticsExtEntry 23 }

    hwXQoSIfCarExtExceededPacketRateHigh OBJECT-TYPE
        SYNTAX Unsigned32
        MAX-ACCESS read-only
        STATUS current
        DESCRIPTION
            "This object indicates the packet rate between PIR and CIR, in pps, which is upper 32 bits of the total number."
        ::= { hwXQoSIfCarStatisticsExtEntry 24 }

    hwXQoSIfCarExtExceededByteRateLow OBJECT-TYPE
        SYNTAX Unsigned32
        MAX-ACCESS read-only
        STATUS current
        DESCRIPTION
            "This object indicates the rate of yellow bytes for the interface CAR, in pps, which is lower 32 bits of the total number."
        ::= { hwXQoSIfCarStatisticsExtEntry 25 }

    hwXQoSIfCarExtExceededByteRateHigh OBJECT-TYPE
        SYNTAX Unsigned32
        MAX-ACCESS read-only
        STATUS current
        DESCRIPTION
            "This object indicates the rate of yellow bytes for the interface CAR, in pps, which is upper 32 bits of the total number."
        ::= { hwXQoSIfCarStatisticsExtEntry 26 }

    hwXQoSIfCarExtOverflowPacketsLow OBJECT-TYPE
        SYNTAX Unsigned32
        MAX-ACCESS read-only
        STATUS current
        DESCRIPTION
            "This object indicates the number of red packets for the interface CAR, which is lower 32 bits of the total number."
        ::= { hwXQoSIfCarStatisticsExtEntry 27 }

    hwXQoSIfCarExtOverflowPacketsHigh OBJECT-TYPE
        SYNTAX Unsigned32
        MAX-ACCESS read-only
        STATUS current
        DESCRIPTION
            "This object indicates the number of red packets for the interface CAR, which is upper 32 bits of the total number."
        ::= { hwXQoSIfCarStatisticsExtEntry 28 }

    hwXQoSIfCarExtOverflowBytesLow OBJECT-TYPE
        SYNTAX Unsigned32
        MAX-ACCESS read-only
        STATUS current
        DESCRIPTION
            "This object indicates the number of red bytes for the interface CAR, which is lower 32 bits of the total number."
        ::= { hwXQoSIfCarStatisticsExtEntry 29 }

    hwXQoSIfCarExtOverflowBytesHigh OBJECT-TYPE
        SYNTAX Unsigned32
        MAX-ACCESS read-only
        STATUS current
        DESCRIPTION
            "This object indicates the number of red bytes for the interface CAR, which is upper 32 bits of the total number."
        ::= { hwXQoSIfCarStatisticsExtEntry 30 }

    hwXQoSIfCarExtOverflowPacketRateLow OBJECT-TYPE
        SYNTAX Unsigned32
        MAX-ACCESS read-only
        STATUS current
        DESCRIPTION
            "This object indicates the rate of red packets for the interface CAR, which is lower 32 bits of the total number."
        ::= { hwXQoSIfCarStatisticsExtEntry 31 }

    hwXQoSIfCarExtOverflowPacketRateHigh OBJECT-TYPE
        SYNTAX Unsigned32
        MAX-ACCESS read-only
        STATUS current
        DESCRIPTION
            "This object indicates the rate of red packets for the interface CAR, which is upper 32 bits of the total number."
        ::= { hwXQoSIfCarStatisticsExtEntry 32 }

    hwXQoSIfExtCarOverflowByteRateLow OBJECT-TYPE
        SYNTAX Unsigned32
        MAX-ACCESS read-only
        STATUS current
        DESCRIPTION
            "This object indicates the rate of red bytes for the interface CAR, which is lower 32 bits of the total number."
        ::= { hwXQoSIfCarStatisticsExtEntry 33 }

    hwXQoSIfExtCarOverflowByteRateHigh OBJECT-TYPE
        SYNTAX Unsigned32
        MAX-ACCESS read-only
        STATUS current
        DESCRIPTION
            "This object indicates the rate of red bytes for the interface CAR, which is upper 32 bits of the total number."
        ::= { hwXQoSIfCarStatisticsExtEntry 34 }

    hwXQoSIfCarExtPassedPacketsLow OBJECT-TYPE
        SYNTAX Unsigned32
        MAX-ACCESS read-only
        STATUS current
        DESCRIPTION
            "This object indicates the number of forwarded packets after CAR is applied, which is lower 32 bits of the total number."
        ::= { hwXQoSIfCarStatisticsExtEntry 35 }

    hwXQoSIfCarExtPassedPacketsHigh OBJECT-TYPE
        SYNTAX Unsigned32
        MAX-ACCESS read-only
        STATUS current
        DESCRIPTION
            "This object indicates the number of forwarded packets after CAR is applied, which is upper 32 bits of the total number."
        ::= { hwXQoSIfCarStatisticsExtEntry 36 }

    hwXQoSIfCarExtPassedBytesLow OBJECT-TYPE
        SYNTAX Unsigned32
        MAX-ACCESS read-only
        STATUS current
        DESCRIPTION
            "This object indicates the number of forwarded bytes after CAR is applied, which is lower 32 bits of the total number."
        ::= { hwXQoSIfCarStatisticsExtEntry 37 }

    hwXQoSIfCarExtPassedBytesHigh OBJECT-TYPE
        SYNTAX Unsigned32
        MAX-ACCESS read-only
        STATUS current
        DESCRIPTION
            "This object indicates the number of forwarded bytes after CAR is applied, which is upper 32 bits of the total number."
        ::= { hwXQoSIfCarStatisticsExtEntry 38 }

    hwXQoSIfCarExtDiscardedPacketsLow OBJECT-TYPE
        SYNTAX Unsigned32
        MAX-ACCESS read-only
        STATUS current
        DESCRIPTION
            "This object indicates the number of discarded packets after CAR is set, which is lower 32 bits of the total number."
        ::= { hwXQoSIfCarStatisticsExtEntry 39 }

    hwXQoSIfCarExtDiscardedPacketsHigh OBJECT-TYPE
        SYNTAX Unsigned32
        MAX-ACCESS read-only
        STATUS current
        DESCRIPTION
            "This object indicates the number of discarded packets after CAR is set, which is upper 32 bits of the total number."
        ::= { hwXQoSIfCarStatisticsExtEntry 40 }

    hwXQoSIfCarExtDiscardedBytesLow OBJECT-TYPE
        SYNTAX Unsigned32
        MAX-ACCESS read-only
        STATUS current
        DESCRIPTION
            "This object indicates the number of discarded bytes after CAR is applied, which is lower 32 bits of the total number."
        ::= { hwXQoSIfCarStatisticsExtEntry 41 }

    hwXQoSIfCarExtDiscardedBytesHigh OBJECT-TYPE
        SYNTAX Unsigned32
        MAX-ACCESS read-only
        STATUS current
        DESCRIPTION
            "This object indicates the number of discarded bytes after CAR is applied, which is upper 32 bits of the total number."
        ::= { hwXQoSIfCarStatisticsExtEntry 42 }
    --***********************************************************

--hwXQoSIfQueueExtRunInfoTable

--************************************************************
--    Queue statistics
    hwXQoSIfQueueExtRunInfoTable OBJECT-TYPE
        SYNTAX SEQUENCE OF HwXQoSIfQueueExtRunInfoEntry
        MAX-ACCESS not-accessible
        STATUS current
        DESCRIPTION
            "This table is used to display the running information about an interface queue."
        ::= { hwXQoSIfStatisticsObjects 12 }

    hwXQoSIfQueueExtRunInfoEntry OBJECT-TYPE
        SYNTAX HwXQoSIfQueueExtRunInfoEntry
        MAX-ACCESS not-accessible
        STATUS current
        DESCRIPTION
            "Queue statistics entry."
        INDEX { hwXQoSIfQueueExtIfIndex, hwXQoSIfQueueExtVlanID, hwXQoSIfQueueExtCosType }
        ::= { hwXQoSIfQueueExtRunInfoTable 1 }

    HwXQoSIfQueueExtRunInfoEntry ::=
        SEQUENCE {
            hwXQoSIfQueueExtIfIndex
                Integer32,
            hwXQoSIfQueueExtVlanID
                Integer32,
            hwXQoSIfQueueExtCosType
                CosType,
            hwXQoSIfQueueExtPassedPacketsLow
                Unsigned32,
            hwXQoSIfQueueExtPassededBytesLow
                Unsigned32,
            hwXQoSIfQueueExtTotalPacketsLow
                Unsigned32,
            hwXQoSIfQueueExtTotalBytesLow
                Unsigned32,
            hwXQoSIfQueueExtDiscardedPacketsLow
                Unsigned32,
            hwXQoSIfQueueExtDiscardedBytesLow
                Unsigned32,
            hwXQoSIfQueueExtPassedPacketRateLow
                Unsigned32,
            hwXQoSIfQueueExtPassedByteRateLow
                Unsigned32,
            hwXQoSIfQueueExtDiscardedPacketRateLow
                Unsigned32,
            hwXQoSIfQueueExtDiscardedByteRateLow
                Unsigned32,
            hwXQoSIfQueueExtPassedPacketsHigh
                Unsigned32,
            hwXQoSIfQueueExtPassededBytesHigh
                Unsigned32,
            hwXQoSIfQueueExtTotalPacketsHigh
                Unsigned32,
            hwXQoSIfQueueExtTotalBytesHigh
                Unsigned32,
            hwXQoSIfQueueExtDiscardedPacketsHigh
                Unsigned32,
            hwXQoSIfQueueExtDiscardedBytesHigh
                Unsigned32,
            hwXQoSIfQueueExtPassedPacketRateHigh
                Unsigned32,
            hwXQoSIfQueueExtPassedByteRateHigh
                Unsigned32,
            hwXQoSIfQueueExtDiscardedPacketRateHigh
                Unsigned32,
            hwXQoSIfQueueExtDiscardedByteRateHigh
                Unsigned32,
            hwXQoSIfQueueExtResetFlag
                ResetFlag,
            hwXQoSIfQueueExtUsagePercentage
                Integer32,
            hwXQoSIfQueueExtDropTailDiscardedPacketsLow
                Unsigned32,
            hwXQoSIfQueueExtDropTailDiscardedBytesLow
                Unsigned32,
            hwXQoSIfQueueExtWredDiscardedPacketsLow
                Unsigned32,
            hwXQoSIfQueueExtWredDiscardedBytesLow
                Unsigned32,
            hwXQoSIfQueueExtDropTailDiscardedPacketRateLow
                Unsigned32,
            hwXQoSIfQueueExtDropTailDiscardedByteRateLow
                Unsigned32,
            hwXQoSIfQueueExtWredDiscardedPacketRateLow
                Unsigned32,
            hwXQoSIfQueueExtWredDiscardedByteRateLow
                Unsigned32,
            hwXQoSIfQueueExtStatisticsTrafficTowardThisPortLow
                Unsigned32,
            hwXQoSIfQueueExtStatisticsPhysicalBandwidthOfPortQoSLow
                Unsigned32,
            hwXQoSIfQueueExtDropTailDiscardedPacketsHigh
                Unsigned32,
            hwXQoSIfQueueExtDropTailDiscardedBytesHigh
                Unsigned32,
            hwXQoSIfQueueExtWredDiscardedPacketsHigh
                Unsigned32,
            hwXQoSIfQueueExtWredDiscardedBytesHigh
                Unsigned32,
            hwXQoSIfQueueExtDropTailDiscardedPacketRateHigh
                Unsigned32,
            hwXQoSIfQueueExtDropTailDiscardedByteRateHigh
                Unsigned32,
            hwXQoSIfQueueExtWredDiscardedPacketRateHigh
                Unsigned32,
            hwXQoSIfQueueExtWredDiscardedByteRateHigh
                Unsigned32,
            hwXQoSIfQueueExtStatisticsTrafficTowardThisPortHigh
                Unsigned32,
            hwXQoSIfQueueExtStatisticsPhysicalBandwidthOfPortQoSHigh
                Unsigned32
         }

    hwXQoSIfQueueExtIfIndex OBJECT-TYPE
        SYNTAX Integer32
        MAX-ACCESS read-only
        STATUS current
        DESCRIPTION
            "The value of this object identifies the interface index."
        ::= { hwXQoSIfQueueExtRunInfoEntry 1 }

    hwXQoSIfQueueExtVlanID OBJECT-TYPE
        SYNTAX Integer32 (0 | 1..4095)
        MAX-ACCESS read-only
        STATUS current
        DESCRIPTION
            "This object indicates the VLAN ID."
        ::= { hwXQoSIfQueueExtRunInfoEntry 2 }

    hwXQoSIfQueueExtCosType OBJECT-TYPE
        SYNTAX CosType
        MAX-ACCESS read-only
        STATUS current
        DESCRIPTION
            "The value of this object identifies COS of the queue. The value can be any of the following: CS7(8), CS6(7), EF(6)
AF4(5),AF3(4),AF2(3),AF1(2),BE(1)."
        ::= { hwXQoSIfQueueExtRunInfoEntry 3 }

    hwXQoSIfQueueExtPassedPacketsLow OBJECT-TYPE
        SYNTAX Unsigned32
        MAX-ACCESS read-only
        STATUS current
        DESCRIPTION
            "This object indicates the number of forwarded packets."
        ::= { hwXQoSIfQueueExtRunInfoEntry 4 }

    hwXQoSIfQueueExtPassedPacketsHigh OBJECT-TYPE
        SYNTAX Unsigned32
        MAX-ACCESS read-only
        STATUS current
        DESCRIPTION
            "This object indicates the number of forwarded packets."
        ::= { hwXQoSIfQueueExtRunInfoEntry 5 }

    hwXQoSIfQueueExtPassededBytesLow OBJECT-TYPE
        SYNTAX Unsigned32
        MAX-ACCESS read-only
        STATUS current
        DESCRIPTION
            "This object indicates the number of bytes that pass the queue. The object has no default value."
        ::= { hwXQoSIfQueueExtRunInfoEntry 6 }

    hwXQoSIfQueueExtPassededBytesHigh OBJECT-TYPE
        SYNTAX Unsigned32
        MAX-ACCESS read-only
        STATUS current
        DESCRIPTION
            "This object indicates the number of bytes that pass the queue. The object has no default value."
        ::= { hwXQoSIfQueueExtRunInfoEntry 7 }

    hwXQoSIfQueueExtTotalPacketsLow OBJECT-TYPE
        SYNTAX Unsigned32
        MAX-ACCESS read-only
        STATUS current
        DESCRIPTION
            "This object indicates the number of packets that reach the queue. The object has no default value."
        ::= { hwXQoSIfQueueExtRunInfoEntry 8 }

    hwXQoSIfQueueExtTotalPacketsHigh OBJECT-TYPE
        SYNTAX Unsigned32
        MAX-ACCESS read-only
        STATUS current
        DESCRIPTION
            "This object indicates the number of packets that reach the queue. The object has no default value."
        ::= { hwXQoSIfQueueExtRunInfoEntry 9 }

    hwXQoSIfQueueExtTotalBytesLow OBJECT-TYPE
        SYNTAX Unsigned32
        MAX-ACCESS read-only
        STATUS current
        DESCRIPTION
            "This object indicates the total number of bytes."
        ::= { hwXQoSIfQueueExtRunInfoEntry 10 }

    hwXQoSIfQueueExtTotalBytesHigh OBJECT-TYPE
        SYNTAX Unsigned32
        MAX-ACCESS read-only
        STATUS current
        DESCRIPTION
            "This object indicates the total number of bytes."
        ::= { hwXQoSIfQueueExtRunInfoEntry 11 }

    hwXQoSIfQueueExtDiscardedPacketsLow OBJECT-TYPE
        SYNTAX Unsigned32
        MAX-ACCESS read-only
        STATUS current
        DESCRIPTION
            "This object indicates the number of discarded packets. "
        ::= { hwXQoSIfQueueExtRunInfoEntry 12 }

    hwXQoSIfQueueExtDiscardedPacketsHigh OBJECT-TYPE
        SYNTAX Unsigned32
        MAX-ACCESS read-only
        STATUS current
        DESCRIPTION
            "This object indicates the number of discarded packets. "
        ::= { hwXQoSIfQueueExtRunInfoEntry 13 }

    hwXQoSIfQueueExtDiscardedBytesLow OBJECT-TYPE
        SYNTAX Unsigned32
        MAX-ACCESS read-only
        STATUS current
        DESCRIPTION
            "This object indicates the number of discarded bytes. "
        ::= { hwXQoSIfQueueExtRunInfoEntry 14 }

    hwXQoSIfQueueExtDiscardedBytesHigh OBJECT-TYPE
        SYNTAX Unsigned32
        MAX-ACCESS read-only
        STATUS current
        DESCRIPTION
            "This object indicates the number of discarded bytes. "
        ::= { hwXQoSIfQueueExtRunInfoEntry 15 }

    hwXQoSIfQueueExtPassedPacketRateLow OBJECT-TYPE
        SYNTAX Unsigned32
        MAX-ACCESS read-only
        STATUS current
        DESCRIPTION
            "This object indicates the rate at which packets are forwarded."
        ::= { hwXQoSIfQueueExtRunInfoEntry 16 }

    hwXQoSIfQueueExtPassedPacketRateHigh OBJECT-TYPE
        SYNTAX Unsigned32
        MAX-ACCESS read-only
        STATUS current
        DESCRIPTION
            "This object indicates the rate at which packets are forwarded."
        ::= { hwXQoSIfQueueExtRunInfoEntry 17 }

    hwXQoSIfQueueExtPassedByteRateLow OBJECT-TYPE
        SYNTAX Unsigned32
        MAX-ACCESS read-only
        STATUS current
        DESCRIPTION
            "This object indicates the rate at which bytes are forwarded. "
        ::= { hwXQoSIfQueueExtRunInfoEntry 18 }

    hwXQoSIfQueueExtPassedByteRateHigh OBJECT-TYPE
        SYNTAX Unsigned32
        MAX-ACCESS read-only
        STATUS current
        DESCRIPTION
            "This object indicates the rate at which bytes are forwarded. "
        ::= { hwXQoSIfQueueExtRunInfoEntry 19 }

    hwXQoSIfQueueExtDiscardedPacketRateLow OBJECT-TYPE
        SYNTAX Unsigned32
        MAX-ACCESS read-only
        STATUS current
        DESCRIPTION
            "This object indicates the packet rate of discarded packets, in pps. The object has no default value."
        ::= { hwXQoSIfQueueExtRunInfoEntry 20 }

    hwXQoSIfQueueExtDiscardedPacketRateHigh OBJECT-TYPE
        SYNTAX Unsigned32
        MAX-ACCESS read-only
        STATUS current
        DESCRIPTION
            "This object indicates the packet rate of discarded packets, in pps. The object has no default value."
        ::= { hwXQoSIfQueueExtRunInfoEntry 21 }

    hwXQoSIfQueueExtDiscardedByteRateLow OBJECT-TYPE
        SYNTAX Unsigned32
        MAX-ACCESS read-only
        STATUS current
        DESCRIPTION
            "This object indicates the rate at which bytes are discarded. "
        ::= { hwXQoSIfQueueExtRunInfoEntry 22 }

    hwXQoSIfQueueExtDiscardedByteRateHigh OBJECT-TYPE
        SYNTAX Unsigned32
        MAX-ACCESS read-only
        STATUS current
        DESCRIPTION
            "This object indicates the rate at which bytes are discarded. "
        ::= { hwXQoSIfQueueExtRunInfoEntry 23 }

    hwXQoSIfQueueExtResetFlag OBJECT-TYPE
        SYNTAX ResetFlag
        MAX-ACCESS read-write
        STATUS current
        DESCRIPTION
            "Reset queue statistics information."
        ::= { hwXQoSIfQueueExtRunInfoEntry 24 }

    hwXQoSIfQueueExtUsagePercentage OBJECT-TYPE
        SYNTAX Integer32
        MAX-ACCESS read-only
        STATUS current
        DESCRIPTION
            "This object indicates the percentage of the queue usage. "
        ::= { hwXQoSIfQueueExtRunInfoEntry 25 }

    hwXQoSIfQueueExtDropTailDiscardedPacketsLow OBJECT-TYPE
        SYNTAX  Unsigned32
        MAX-ACCESS read-only
        STATUS current
        DESCRIPTION
            " The value of this object identifies the number of discarded tail packets. "
        ::= { hwXQoSIfQueueExtRunInfoEntry 26 }

    hwXQoSIfQueueExtDropTailDiscardedPacketsHigh OBJECT-TYPE
        SYNTAX  Unsigned32
        MAX-ACCESS read-only
        STATUS current
        DESCRIPTION
            " The value of this object identifies the number of discarded tail packets. "
        ::= { hwXQoSIfQueueExtRunInfoEntry 27 }

    hwXQoSIfQueueExtDropTailDiscardedBytesLow OBJECT-TYPE
        SYNTAX  Unsigned32
        MAX-ACCESS read-only
        STATUS current
        DESCRIPTION
            " This object indicates the number of bytes discarded by tail drop. "
        ::= { hwXQoSIfQueueExtRunInfoEntry 28 }

    hwXQoSIfQueueExtDropTailDiscardedBytesHigh OBJECT-TYPE
        SYNTAX  Unsigned32
        MAX-ACCESS read-only
        STATUS current
        DESCRIPTION
            " This object indicates the number of bytes discarded by tail drop. "
        ::= { hwXQoSIfQueueExtRunInfoEntry 29 }

    hwXQoSIfQueueExtWredDiscardedPacketsLow OBJECT-TYPE
        SYNTAX  Unsigned32
        MAX-ACCESS read-only
        STATUS current
        DESCRIPTION
            " The value of this object identifies the number of packets that are discarded by WRED. "
        ::= { hwXQoSIfQueueExtRunInfoEntry 30 }

    hwXQoSIfQueueExtWredDiscardedPacketsHigh OBJECT-TYPE
        SYNTAX  Unsigned32
        MAX-ACCESS read-only
        STATUS current
        DESCRIPTION
            " The value of this object identifies the number of packets that are discarded by WRED. "
        ::= { hwXQoSIfQueueExtRunInfoEntry 31 }

    hwXQoSIfQueueExtWredDiscardedBytesLow OBJECT-TYPE
        SYNTAX  Unsigned32
        MAX-ACCESS read-only
        STATUS current
        DESCRIPTION
            "This object indicates the number of bytes discarded by WRED. "
        ::= { hwXQoSIfQueueExtRunInfoEntry 32 }

    hwXQoSIfQueueExtWredDiscardedBytesHigh OBJECT-TYPE
        SYNTAX  Unsigned32
        MAX-ACCESS read-only
        STATUS current
        DESCRIPTION
            "This object indicates the number of bytes discarded by WRED. "
        ::= { hwXQoSIfQueueExtRunInfoEntry 33 }

    hwXQoSIfQueueExtDropTailDiscardedPacketRateLow OBJECT-TYPE
        SYNTAX  Unsigned32
        MAX-ACCESS read-only
        STATUS current
        DESCRIPTION
            " This object indicates the tail packet discarding rate. "
        ::= { hwXQoSIfQueueExtRunInfoEntry 34 }

    hwXQoSIfQueueExtDropTailDiscardedPacketRateHigh OBJECT-TYPE
        SYNTAX  Unsigned32
        MAX-ACCESS read-only
        STATUS current
        DESCRIPTION
            " This object indicates the tail packet discarding rate. "
        ::= { hwXQoSIfQueueExtRunInfoEntry 35 }

    hwXQoSIfQueueExtDropTailDiscardedByteRateLow OBJECT-TYPE
        SYNTAX  Unsigned32
        MAX-ACCESS read-only
        STATUS current
        DESCRIPTION
            "This object indicates the rate at which packets are discarded by tail drop. "
        ::= { hwXQoSIfQueueExtRunInfoEntry 36 }

    hwXQoSIfQueueExtDropTailDiscardedByteRateHigh OBJECT-TYPE
        SYNTAX  Unsigned32
        MAX-ACCESS read-only
        STATUS current
        DESCRIPTION
            "This object indicates the rate at which packets are discarded by tail drop. "
        ::= { hwXQoSIfQueueExtRunInfoEntry 37 }

    hwXQoSIfQueueExtWredDiscardedPacketRateLow OBJECT-TYPE
        SYNTAX  Unsigned32
        MAX-ACCESS read-only
        STATUS current
        DESCRIPTION
            " This object indicates the WRED packet discarding rate."
        ::= { hwXQoSIfQueueExtRunInfoEntry 38 }

    hwXQoSIfQueueExtWredDiscardedPacketRateHigh OBJECT-TYPE
        SYNTAX  Unsigned32
        MAX-ACCESS read-only
        STATUS current
        DESCRIPTION
            " This object indicates the WRED packet discarding rate."
        ::= { hwXQoSIfQueueExtRunInfoEntry 39 }

    hwXQoSIfQueueExtWredDiscardedByteRateLow OBJECT-TYPE
        SYNTAX  Unsigned32
        MAX-ACCESS read-only
        STATUS current
        DESCRIPTION
            " This object indicates the rate at which packets are discarded by WRED."
        ::= { hwXQoSIfQueueExtRunInfoEntry 40 }

    hwXQoSIfQueueExtWredDiscardedByteRateHigh OBJECT-TYPE
        SYNTAX  Unsigned32
        MAX-ACCESS read-only
        STATUS current
        DESCRIPTION
            " This object indicates the rate at which packets are discarded by WRED."
        ::= { hwXQoSIfQueueExtRunInfoEntry 41 }

    hwXQoSIfQueueExtStatisticsTrafficTowardThisPortLow OBJECT-TYPE
        SYNTAX  Unsigned32
        MAX-ACCESS read-only
        STATUS current
        DESCRIPTION
            " This object indicates the traffic which towards this port."
        ::= { hwXQoSIfQueueExtRunInfoEntry 42 }

    hwXQoSIfQueueExtStatisticsTrafficTowardThisPortHigh OBJECT-TYPE
        SYNTAX  Unsigned32
        MAX-ACCESS read-only
        STATUS current
        DESCRIPTION
            " This object indicates the traffic which towards this port."
        ::= { hwXQoSIfQueueExtRunInfoEntry 43 }

    hwXQoSIfQueueExtStatisticsPhysicalBandwidthOfPortQoSLow OBJECT-TYPE
        SYNTAX  Unsigned32
        MAX-ACCESS read-only
        STATUS current
        DESCRIPTION
            " This object indicates the physical bandwidth of a QoS interface."
        ::= { hwXQoSIfQueueExtRunInfoEntry 44 }

    hwXQoSIfQueueExtStatisticsPhysicalBandwidthOfPortQoSHigh OBJECT-TYPE
        SYNTAX  Unsigned32
        MAX-ACCESS read-only
        STATUS current
        DESCRIPTION
            " This object indicates the physical bandwidth of a QoS interface."
        ::= { hwXQoSIfQueueExtRunInfoEntry 45 }
  -- vlan stat
    hwXQoSVlanStatisticsObjects OBJECT IDENTIFIER ::= { hwXQoSStatisticsObjects 4 }

    hwXQosVlanStatTable OBJECT-TYPE
        SYNTAX SEQUENCE OF HwXQosVlanStatEntry
        MAX-ACCESS not-accessible
        STATUS current
        DESCRIPTION
            "The table contains statistics information for the vlan."
        ::= { hwXQoSVlanStatisticsObjects 1 }

    hwXQosVlanStatEntry OBJECT-TYPE
        SYNTAX HwXQosVlanStatEntry
        MAX-ACCESS not-accessible
        STATUS current
        DESCRIPTION
            "Entries of vlan statistics table."
        INDEX { hwXQosVlanStatVlanId }
        ::= { hwXQosVlanStatTable 1 }

    HwXQosVlanStatEntry ::=
        SEQUENCE {
            hwXQosVlanStatVlanId
                Integer32,
            hwXQosVlanStatInTotalPkts
                Counter64,
            hwXQosVlanStatInTotalBytes
                Counter64,
            hwXQosVlanStatOutTotalPkts
                Counter64,
            hwXQosVlanStatOutTotalBytes
                Counter64,
            hwXQosVlanStatInUcastPkts
                Counter64,
            hwXQosVlanStatInUcastBytes
                Counter64,
            hwXQosVlanStatOutUcastPkts
                Counter64,
            hwXQosVlanStatOutUcastBytes
                Counter64,
            hwXQosVlanStatInMcastPkts
                Counter64,
            hwXQosVlanStatInMcastBytes
                Counter64,
            hwXQosVlanStatOutMcastPkts
                Counter64,
            hwXQosVlanStatOutMcastBytes
                Counter64,
            hwXQosVlanStatInBcastPkts
                Counter64,
            hwXQosVlanStatInBcastBytes
                Counter64,
            hwXQosVlanStatOutBcastPkts
                Counter64,
            hwXQosVlanStatOutBcastBytes
                Counter64,
            hwXQosVlanStatInUnknownUcastPkts
                Counter64,
            hwXQosVlanStatInUnknownUcastBytes
                Counter64,
            hwXQosVlanStatResetFlag
                EnabledStatus,
            hwXQosVlanStatInTotalPktsRate
                Counter64,
            hwXQosVlanStatInTotalBytesRate
                Counter64,
            hwXQosVlanStatOutTotalPktsRate
                Counter64,
            hwXQosVlanStatOutTotalBytesRate
                Counter64,
            hwXQosVlanStatInMcastTotalPktsRate
                Counter64,
            hwXQosVlanStatInMcastTotalBytesRate
                Counter64,
            hwXQosVlanStatInBcastTotalPktsRate
                Counter64,
            hwXQosVlanStatInBcastTotalBytesRate
                Counter64,
            hwXQosVlanStatInUnknownUcastTotalPktsRate
                Counter64,
            hwXQosVlanStatInUnknownUcastTotalBytesRate
                Counter64,
            hwXQosVlanStatInDropTotalPktsRate
                Counter64,
            hwXQosVlanStatInDropTotalBytesRate
                Counter64,
            hwXQosVlanStatInDropPercentageTotalBytesRate
                Counter64
            }

    hwXQosVlanStatVlanId OBJECT-TYPE
        SYNTAX Integer32 (0 | 1..4094)
        MAX-ACCESS not-accessible
        STATUS current
        DESCRIPTION
            "The id of vlan."
        ::= { hwXQosVlanStatEntry 1 }

    hwXQosVlanStatInTotalPkts OBJECT-TYPE
        SYNTAX Counter64
        MAX-ACCESS read-only
        STATUS current
        DESCRIPTION
            "The number of received packets."
        ::= { hwXQosVlanStatEntry 2 }

    hwXQosVlanStatInTotalBytes OBJECT-TYPE
        SYNTAX Counter64
        MAX-ACCESS read-only
        STATUS current
        DESCRIPTION
            "The byte number of received packets."
        ::= { hwXQosVlanStatEntry 3 }

    hwXQosVlanStatOutTotalPkts OBJECT-TYPE
        SYNTAX Counter64
        MAX-ACCESS read-only
        STATUS current
        DESCRIPTION
            "The number of transmittable packets."
        ::= { hwXQosVlanStatEntry 4 }

    hwXQosVlanStatOutTotalBytes OBJECT-TYPE
        SYNTAX Counter64
        MAX-ACCESS read-only
        STATUS current
        DESCRIPTION
            "The byte number of transmittable packets."
        ::= { hwXQosVlanStatEntry 5 }

    hwXQosVlanStatInUcastPkts OBJECT-TYPE
        SYNTAX Counter64
        MAX-ACCESS read-only
        STATUS current
        DESCRIPTION
            "The number of received unicast packets."
        ::= { hwXQosVlanStatEntry 6 }

    hwXQosVlanStatInUcastBytes OBJECT-TYPE
        SYNTAX Counter64
        MAX-ACCESS read-only
        STATUS current
        DESCRIPTION
            "The number of received unicast packets' bytes."
        ::= { hwXQosVlanStatEntry 7 }

    hwXQosVlanStatOutUcastPkts OBJECT-TYPE
        SYNTAX Counter64
        MAX-ACCESS read-only
        STATUS current
        DESCRIPTION
            "The number of transmittable unicast packets."
        ::= { hwXQosVlanStatEntry 8 }

    hwXQosVlanStatOutUcastBytes OBJECT-TYPE
        SYNTAX Counter64
        MAX-ACCESS read-only
        STATUS current
        DESCRIPTION
            "The number of transmittable unicast packets' bytes."
        ::= { hwXQosVlanStatEntry 9 }

    hwXQosVlanStatInMcastPkts OBJECT-TYPE
        SYNTAX Counter64
        MAX-ACCESS read-only
        STATUS current
        DESCRIPTION
            "The number of received multicast packets."
        ::= { hwXQosVlanStatEntry 10 }

    hwXQosVlanStatInMcastBytes OBJECT-TYPE
        SYNTAX Counter64
        MAX-ACCESS read-only
        STATUS current
        DESCRIPTION
            "The number of received multicast packets' bytes."
        ::= { hwXQosVlanStatEntry 11 }

    hwXQosVlanStatOutMcastPkts OBJECT-TYPE
        SYNTAX Counter64
        MAX-ACCESS read-only
        STATUS current
        DESCRIPTION
            "The number of transmittable multicast packets."
        ::= { hwXQosVlanStatEntry 12 }

    hwXQosVlanStatOutMcastBytes OBJECT-TYPE
        SYNTAX Counter64
        MAX-ACCESS read-only
        STATUS current
        DESCRIPTION
            "The number of transmittable multicast packets' bytes."
        ::= { hwXQosVlanStatEntry 13 }

    hwXQosVlanStatInBcastPkts OBJECT-TYPE
        SYNTAX Counter64
        MAX-ACCESS read-only
        STATUS current
        DESCRIPTION
            "The number of received broadcast packets."
        ::= { hwXQosVlanStatEntry 14 }

    hwXQosVlanStatInBcastBytes OBJECT-TYPE
        SYNTAX Counter64
        MAX-ACCESS read-only
        STATUS current
        DESCRIPTION
            "The number of received broadcast packets' bytes."
        ::= { hwXQosVlanStatEntry 15 }

    hwXQosVlanStatOutBcastPkts OBJECT-TYPE
        SYNTAX Counter64
        MAX-ACCESS read-only
        STATUS current
        DESCRIPTION
            "The number of transmittable broadcast packets."
        ::= { hwXQosVlanStatEntry 16 }

    hwXQosVlanStatOutBcastBytes OBJECT-TYPE
        SYNTAX Counter64
        MAX-ACCESS read-only
        STATUS current
        DESCRIPTION
            "The number of transmittable broadcast packets."
        ::= { hwXQosVlanStatEntry 17 }

    hwXQosVlanStatInUnknownUcastPkts OBJECT-TYPE
        SYNTAX Counter64
        MAX-ACCESS read-only
        STATUS current
        DESCRIPTION
            "The number of received unknown broadcast packets."
        ::= { hwXQosVlanStatEntry 18 }

    hwXQosVlanStatInUnknownUcastBytes OBJECT-TYPE
        SYNTAX Counter64
        MAX-ACCESS read-only
        STATUS current
        DESCRIPTION
            "The number of received unknown broadcast packets' bytes."
        ::= { hwXQosVlanStatEntry 19 }

    hwXQosVlanStatResetFlag OBJECT-TYPE
        SYNTAX EnabledStatus
        MAX-ACCESS read-create
        STATUS current
        DESCRIPTION
            "The flag of reset."
        ::= { hwXQosVlanStatEntry 20 }
    hwXQosVlanStatInTotalPktsRate OBJECT-TYPE
        SYNTAX Counter64
        MAX-ACCESS read-only
        STATUS current
        DESCRIPTION
            "The rate of received packets."
        ::= { hwXQosVlanStatEntry 21 }

    hwXQosVlanStatInTotalBytesRate OBJECT-TYPE
        SYNTAX Counter64
        MAX-ACCESS read-only
        STATUS current
        DESCRIPTION
            "The rate of received bytes."
        ::= { hwXQosVlanStatEntry 22 }

    hwXQosVlanStatOutTotalPktsRate OBJECT-TYPE
        SYNTAX Counter64
        MAX-ACCESS read-only
        STATUS current
        DESCRIPTION
            "The rate of transmittable packets."
        ::= { hwXQosVlanStatEntry 23 }

    hwXQosVlanStatOutTotalBytesRate OBJECT-TYPE
        SYNTAX Counter64
        MAX-ACCESS read-only
        STATUS current
        DESCRIPTION
            "The rate of transmittable bytes."
        ::= { hwXQosVlanStatEntry 24 }

    hwXQosVlanStatInMcastTotalPktsRate OBJECT-TYPE
        SYNTAX Counter64
        MAX-ACCESS read-only
        STATUS current
        DESCRIPTION
            "The rate of transmittable packets."
        ::= { hwXQosVlanStatEntry 25 }

    hwXQosVlanStatInMcastTotalBytesRate OBJECT-TYPE
        SYNTAX Counter64
        MAX-ACCESS read-only
        STATUS current
        DESCRIPTION
            "The rate of transmittable bytes."
        ::= { hwXQosVlanStatEntry 26 }

    hwXQosVlanStatInBcastTotalPktsRate OBJECT-TYPE
        SYNTAX Counter64
        MAX-ACCESS read-only
        STATUS current
        DESCRIPTION
            "The rate of transmittable packets."
        ::= { hwXQosVlanStatEntry 27 }

    hwXQosVlanStatInBcastTotalBytesRate OBJECT-TYPE
        SYNTAX Counter64
        MAX-ACCESS read-only
        STATUS current
        DESCRIPTION
            "The rate of transmittable bytes."
        ::= { hwXQosVlanStatEntry 28 }

    hwXQosVlanStatInUnknownUcastTotalPktsRate OBJECT-TYPE
        SYNTAX Counter64
        MAX-ACCESS read-only
        STATUS current
        DESCRIPTION
            "The rate of transmittable packets."
        ::= { hwXQosVlanStatEntry 29 }

    hwXQosVlanStatInUnknownUcastTotalBytesRate OBJECT-TYPE
        SYNTAX Counter64
        MAX-ACCESS read-only
        STATUS current
        DESCRIPTION
            "The rate of transmittable bytes."
        ::= { hwXQosVlanStatEntry 30 }
    hwXQosVlanStatInDropTotalPktsRate OBJECT-TYPE
        SYNTAX Counter64
        MAX-ACCESS read-only
        STATUS current
        DESCRIPTION
            "The rate of transmittable packets."
        ::= { hwXQosVlanStatEntry 31 }

    hwXQosVlanStatInDropTotalBytesRate OBJECT-TYPE
        SYNTAX Counter64
        MAX-ACCESS read-only
        STATUS current
        DESCRIPTION
            "The rate of transmittable bytes."
        ::= { hwXQosVlanStatEntry 32 }

    hwXQosVlanStatInDropPercentageTotalBytesRate OBJECT-TYPE
        SYNTAX Counter64
        MAX-ACCESS read-only
        STATUS current
        DESCRIPTION
            "The Percentage number of droped packets."
        ::= { hwXQosVlanStatEntry 33 }

--???????
    hwXQosVlanSlotStatTable OBJECT-TYPE
        SYNTAX SEQUENCE OF HwXQosVlanSlotStatEntry
        MAX-ACCESS not-accessible
        STATUS current
        DESCRIPTION
            "The table contains statistics information for the vlan of board."
        ::= { hwXQoSVlanStatisticsObjects 2 }

    hwXQosVlanSlotStatEntry OBJECT-TYPE
        SYNTAX HwXQosVlanSlotStatEntry
        MAX-ACCESS not-accessible
        STATUS current
        DESCRIPTION
            "Entries of vlan statistics on board table."
        INDEX { hwXQosVlanSlotStatVlanId,hwXQosVlanSlotStatSlotId }
        ::= { hwXQosVlanSlotStatTable 1 }

    HwXQosVlanSlotStatEntry ::=
        SEQUENCE {
            hwXQosVlanSlotStatVlanId
                Integer32,
            hwXQosVlanSlotStatSlotId
                Integer32,
            hwXQosVlanSlotStatInPkts
                Counter64,
            hwXQosVlanSlotStatInPktsRate
                Counter64,
            hwXQosVlanSlotStatInBytes
                Counter64,
            hwXQosVlanSlotStatInBytesRate
                Counter64,
            hwXQosVlanSlotStatOutPkts
                Counter64,
            hwXQosVlanSlotStatOutPktsRate
                Counter64,
            hwXQosVlanSlotStatOutBytes
                Counter64,
            hwXQosVlanSlotStatOutBytesRate
                Counter64,
            hwXQosVlanSlotStatInMcastPkts
                Counter64,
            hwXQosVlanSlotStatInMcastPktsRate
                Counter64,
            hwXQosVlanSlotStatInMcastBytes
                Counter64,
            hwXQosVlanSlotStatInMcastBytesRate
                Counter64,
            hwXQosVlanSlotStatInBcastPkts
                Counter64,
            hwXQosVlanSlotStatInBcastPktsRate
                Counter64,
            hwXQosVlanSlotStatInBcastBytes
                Counter64,
            hwXQosVlanSlotStatInBcastBytesRate
                Counter64,
            hwXQosVlanSlotStatInUnknownUcastPkts
                Counter64,
            hwXQosVlanSlotStatInUnknownUcastPktsRate
                Counter64,
            hwXQosVlanSlotStatInUnknownUcastBytes
                Counter64,
            hwXQosVlanSlotStatInUnknownUcastBytesRate
                Counter64,
            hwXQosVlanSlotStatInDropPkts
                Counter64,
            hwXQosVlanSlotStatInDropPktsRate
                Counter64,
            hwXQosVlanSlotStatInDropBytes
                Counter64,
            hwXQosVlanSlotStatInDropBytesRate
                Counter64,
            hwXQosVlanSlotStatInDropPercentageBytesRate
                Counter64
            }

    hwXQosVlanSlotStatVlanId OBJECT-TYPE
        SYNTAX Integer32 (0 | 1..4094)
        MAX-ACCESS not-accessible
        STATUS current
        DESCRIPTION
            "The id of vlan."
        ::= { hwXQosVlanSlotStatEntry 1 }

        hwXQosVlanSlotStatSlotId OBJECT-TYPE
        SYNTAX Integer32 (0 | 1..5000)
        MAX-ACCESS not-accessible
        STATUS current
        DESCRIPTION
            "The id of slot."
        ::= { hwXQosVlanSlotStatEntry 2 }

 --in
    hwXQosVlanSlotStatInPkts OBJECT-TYPE
        SYNTAX Counter64
        MAX-ACCESS read-only
        STATUS current
        DESCRIPTION
            "The number of received packets."
        ::= { hwXQosVlanSlotStatEntry 3 }

    hwXQosVlanSlotStatInPktsRate OBJECT-TYPE
        SYNTAX Counter64
        MAX-ACCESS read-only
        STATUS current
        DESCRIPTION
            "The rate of received packets by number."
        ::= { hwXQosVlanSlotStatEntry 4 }

    hwXQosVlanSlotStatInBytes OBJECT-TYPE
        SYNTAX Counter64
        MAX-ACCESS read-only
        STATUS current
        DESCRIPTION
            "The byte number of received packets."
        ::= { hwXQosVlanSlotStatEntry 5 }

    hwXQosVlanSlotStatInBytesRate OBJECT-TYPE
        SYNTAX Counter64
        MAX-ACCESS read-only
        STATUS current
        DESCRIPTION
            "The rate of received packets by bytes."
        ::= { hwXQosVlanSlotStatEntry 6 }

--out

    hwXQosVlanSlotStatOutPkts OBJECT-TYPE
        SYNTAX Counter64
        MAX-ACCESS read-only
        STATUS current
        DESCRIPTION
            "The number of transmittable packets."
        ::= { hwXQosVlanSlotStatEntry 7 }

    hwXQosVlanSlotStatOutPktsRate OBJECT-TYPE
        SYNTAX Counter64
        MAX-ACCESS read-only
        STATUS current
        DESCRIPTION
            "The rate of transmittable packets by bytes."
        ::= { hwXQosVlanSlotStatEntry 8 }

    hwXQosVlanSlotStatOutBytes OBJECT-TYPE
        SYNTAX Counter64
        MAX-ACCESS read-only
        STATUS current
        DESCRIPTION
            "The byte number of transmittable packets."
        ::= { hwXQosVlanSlotStatEntry 9 }

    hwXQosVlanSlotStatOutBytesRate OBJECT-TYPE
        SYNTAX Counter64
        MAX-ACCESS read-only
        STATUS current
        DESCRIPTION
            "The rate number of transmittable packets by bytes."
        ::= { hwXQosVlanSlotStatEntry 10 }

--multicast

    hwXQosVlanSlotStatInMcastPkts OBJECT-TYPE
        SYNTAX Counter64
        MAX-ACCESS read-only
        STATUS current
        DESCRIPTION
            "The number of received multicast packets."
        ::= { hwXQosVlanSlotStatEntry 11 }

    hwXQosVlanSlotStatInMcastPktsRate OBJECT-TYPE
        SYNTAX Counter64
        MAX-ACCESS read-only
        STATUS current
        DESCRIPTION
            "The rate of received multicast packets ."
        ::= { hwXQosVlanSlotStatEntry 12 }

    hwXQosVlanSlotStatInMcastBytes OBJECT-TYPE
        SYNTAX Counter64
        MAX-ACCESS read-only
        STATUS current
        DESCRIPTION
            "The number of received multicast packets' bytes."
        ::= { hwXQosVlanSlotStatEntry 13 }

    hwXQosVlanSlotStatInMcastBytesRate OBJECT-TYPE
        SYNTAX Counter64
        MAX-ACCESS read-only
        STATUS current
        DESCRIPTION
            "The rate of received multicast packets' bytes."
        ::= { hwXQosVlanSlotStatEntry 14 }

--broadcast
    hwXQosVlanSlotStatInBcastPkts OBJECT-TYPE
        SYNTAX Counter64
        MAX-ACCESS read-only
        STATUS current
        DESCRIPTION
            "The number of received broadcast packets."
        ::= { hwXQosVlanSlotStatEntry 15 }

    hwXQosVlanSlotStatInBcastPktsRate OBJECT-TYPE
        SYNTAX Counter64
        MAX-ACCESS read-only
        STATUS current
        DESCRIPTION
            "The rate of received broadcast packets."
        ::= { hwXQosVlanSlotStatEntry 16 }

    hwXQosVlanSlotStatInBcastBytes OBJECT-TYPE
        SYNTAX Counter64
        MAX-ACCESS read-only
        STATUS current
        DESCRIPTION
            "The number of received broadcast packets' bytes."
        ::= { hwXQosVlanSlotStatEntry 17 }

    hwXQosVlanSlotStatInBcastBytesRate OBJECT-TYPE
        SYNTAX Counter64
        MAX-ACCESS read-only
        STATUS current
        DESCRIPTION
            "The rate of received broadcast packets' bytes."
        ::= { hwXQosVlanSlotStatEntry 18 }

-- unknown-ucast
    hwXQosVlanSlotStatInUnknownUcastPkts OBJECT-TYPE
        SYNTAX Counter64
        MAX-ACCESS read-only
        STATUS current
        DESCRIPTION
            "The number of received unknown broadcast packets."
        ::= { hwXQosVlanSlotStatEntry 19 }

    hwXQosVlanSlotStatInUnknownUcastPktsRate OBJECT-TYPE
        SYNTAX Counter64
        MAX-ACCESS read-only
        STATUS current
        DESCRIPTION
            "The rate of received unknown broadcast packets."
        ::= { hwXQosVlanSlotStatEntry 20 }

    hwXQosVlanSlotStatInUnknownUcastBytes OBJECT-TYPE
        SYNTAX Counter64
        MAX-ACCESS read-only
        STATUS current
        DESCRIPTION
            "The number of received unknown broadcast packets' bytes."
        ::= { hwXQosVlanSlotStatEntry 21 }

    hwXQosVlanSlotStatInUnknownUcastBytesRate OBJECT-TYPE
        SYNTAX Counter64
        MAX-ACCESS read-only
        STATUS current
        DESCRIPTION
            "The rate of received unknown broadcast packets' bytes."
        ::= { hwXQosVlanSlotStatEntry 22 }
--drop
    hwXQosVlanSlotStatInDropPkts OBJECT-TYPE
        SYNTAX Counter64
        MAX-ACCESS read-only
        STATUS current
        DESCRIPTION
            "The number of droped packets."
        ::= { hwXQosVlanSlotStatEntry 23 }
    hwXQosVlanSlotStatInDropPktsRate OBJECT-TYPE
        SYNTAX Counter64
        MAX-ACCESS read-only
        STATUS current
        DESCRIPTION
            "The rate of droped packets."
        ::= { hwXQosVlanSlotStatEntry 24 }

    hwXQosVlanSlotStatInDropBytes OBJECT-TYPE
        SYNTAX Counter64
        MAX-ACCESS read-only
        STATUS current
        DESCRIPTION
            "The number of droped bytes."
        ::= { hwXQosVlanSlotStatEntry 25 }

    hwXQosVlanSlotStatInDropBytesRate OBJECT-TYPE
        SYNTAX Counter64
        MAX-ACCESS read-only
        STATUS current
        DESCRIPTION
            "The rate of droped bytes."
        ::= { hwXQosVlanSlotStatEntry 26 }

    hwXQosVlanSlotStatInDropPercentageBytesRate OBJECT-TYPE
        SYNTAX Counter64
        MAX-ACCESS read-only
        STATUS current
        DESCRIPTION
            "The rate of droped bytes."
        ::= { hwXQosVlanSlotStatEntry 27 }

-- buffer usage stat
    hwXQoSBufferUsageStatisticsObjects OBJECT IDENTIFIER ::= { hwXQoSStatisticsObjects 5 }

    --slot buffer usage
    hwXQoSBufferUsageSlotStatTable OBJECT-TYPE
        SYNTAX SEQUENCE OF HwXQoSBufferUsageSlotStatEntry
        MAX-ACCESS not-accessible
        STATUS current
        DESCRIPTION
            "The table contains statistics information for slot buffer usage."
        ::= { hwXQoSBufferUsageStatisticsObjects 1 }

    hwXQoSBufferUsageSlotStatEntry OBJECT-TYPE
        SYNTAX HwXQoSBufferUsageSlotStatEntry
        MAX-ACCESS not-accessible
        STATUS current
        DESCRIPTION
            "Entries of slot buffer usage statistics table."
        INDEX { hwXQosBufferUsageSlotStatFrameId, hwXQosBufferUsageSlotStatSlotId }
        ::= { hwXQoSBufferUsageSlotStatTable 1 }

    HwXQoSBufferUsageSlotStatEntry ::=
        SEQUENCE {
            hwXQosBufferUsageSlotStatFrameId
                Integer32,
            hwXQosBufferUsageSlotStatSlotId
                Integer32,
            hwXQosBufferUsageSlotStatTotalLength
                Counter64,
            hwXQosBufferUsageSlotStatUsedLength
                Counter64,
            hwXQosBufferUsageSlotStatRemainedLength
                Counter64,
            hwXQosBufferUsageSlotStatPeakUsedLength
                Counter64,
            hwXQosBufferUsageSlotStatAverageUsedLength
                Counter64
            }

    hwXQosBufferUsageSlotStatFrameId OBJECT-TYPE
        SYNTAX Integer32
        MAX-ACCESS not-accessible
        STATUS current
        DESCRIPTION
            "The frame id of the device."
        ::= { hwXQoSBufferUsageSlotStatEntry 1 }

    hwXQosBufferUsageSlotStatSlotId OBJECT-TYPE
        SYNTAX Integer32
        MAX-ACCESS not-accessible
        STATUS current
        DESCRIPTION
            "The slot id of the device."
        ::= { hwXQoSBufferUsageSlotStatEntry 2 }

    hwXQosBufferUsageSlotStatTotalLength OBJECT-TYPE
        SYNTAX Counter64
        MAX-ACCESS read-only
        STATUS current
        DESCRIPTION
            "The total kbyte number of slot buffer."
        ::= { hwXQoSBufferUsageSlotStatEntry 3 }

    hwXQosBufferUsageSlotStatUsedLength OBJECT-TYPE
        SYNTAX Counter64
        MAX-ACCESS read-only
        STATUS current
        DESCRIPTION
            "The used kbyte number of slot buffer."
        ::= { hwXQoSBufferUsageSlotStatEntry 4 }

    hwXQosBufferUsageSlotStatRemainedLength OBJECT-TYPE
        SYNTAX Counter64
        MAX-ACCESS read-only
        STATUS current
        DESCRIPTION
            "The remained kbyte number of slot buffer."
        ::= { hwXQoSBufferUsageSlotStatEntry 5 }

    hwXQosBufferUsageSlotStatPeakUsedLength OBJECT-TYPE
        SYNTAX Counter64
        MAX-ACCESS read-only
        STATUS current
        DESCRIPTION
            "The used kbyte number of slot buffer."
        ::= { hwXQoSBufferUsageSlotStatEntry 6 }

    hwXQosBufferUsageSlotStatAverageUsedLength OBJECT-TYPE
        SYNTAX Counter64
        MAX-ACCESS read-only
        STATUS current
        DESCRIPTION
            "The used kbyte number of slot buffer."
        ::= { hwXQoSBufferUsageSlotStatEntry 7 }

--interface buffer usage
    hwXQoSBufferUsageIfStatTable OBJECT-TYPE
        SYNTAX SEQUENCE OF HwXQoSBufferUsageIfStatEntry
        MAX-ACCESS not-accessible
        STATUS current
        DESCRIPTION
            "The table contains statistics information for interface buffer usage."
        ::= { hwXQoSBufferUsageStatisticsObjects 2 }

    hwXQoSBufferUsageIfStatEntry OBJECT-TYPE
        SYNTAX HwXQoSBufferUsageIfStatEntry
        MAX-ACCESS not-accessible
        STATUS current
        DESCRIPTION
            "Entries of interface buffer usage statistics table."
        INDEX { hwXQosBufferUsageIfStatIfindex }
        ::= { hwXQoSBufferUsageIfStatTable 1 }

    HwXQoSBufferUsageIfStatEntry ::=
        SEQUENCE {
            hwXQosBufferUsageIfStatIfindex
                Integer32,
            hwXQosBufferUsageIfStatTotalLength
                Counter64,
            hwXQosBufferUsageIfStatUsedLength
                Counter64,
            hwXQosBufferUsageIfStatRemainedLength
                Counter64,
            hwXQosBufferUsageIfStatPeakUsedLength
                Counter64,
            hwXQosBufferUsageIfStatAverageUsedLength
                Counter64
            }

    hwXQosBufferUsageIfStatIfindex OBJECT-TYPE
        SYNTAX Integer32
        MAX-ACCESS not-accessible
        STATUS current
        DESCRIPTION
            "The interface index."
        ::= { hwXQoSBufferUsageIfStatEntry 1 }

    hwXQosBufferUsageIfStatTotalLength OBJECT-TYPE
        SYNTAX Counter64
        MAX-ACCESS read-only
        STATUS current
        DESCRIPTION
            "The total kbyte number of interface buffer."
        ::= { hwXQoSBufferUsageIfStatEntry 2 }

    hwXQosBufferUsageIfStatUsedLength OBJECT-TYPE
        SYNTAX Counter64
        MAX-ACCESS read-only
        STATUS current
        DESCRIPTION
            "The used kbyte number of interface buffer."
        ::= { hwXQoSBufferUsageIfStatEntry 3 }

    hwXQosBufferUsageIfStatRemainedLength OBJECT-TYPE
        SYNTAX Counter64
        MAX-ACCESS read-only
        STATUS current
        DESCRIPTION
            "The remained kbyte number of interface buffer."
        ::= { hwXQoSBufferUsageIfStatEntry 4 }

    hwXQosBufferUsageIfStatPeakUsedLength OBJECT-TYPE
        SYNTAX Counter64
        MAX-ACCESS read-only
        STATUS current
        DESCRIPTION
            "The used kbyte number of interface buffer."
        ::= { hwXQoSBufferUsageIfStatEntry 5 }

    hwXQosBufferUsageIfStatAverageUsedLength OBJECT-TYPE
        SYNTAX Counter64
        MAX-ACCESS read-only
        STATUS current
        DESCRIPTION
            "The used kbyte number of interface buffer."
        ::= { hwXQoSBufferUsageIfStatEntry 6 }

--interface queue buffer usage
    hwXQoSBufferUsageQueueStatTable OBJECT-TYPE
        SYNTAX SEQUENCE OF HwXQoSBufferUsageQueueStatEntry
        MAX-ACCESS not-accessible
        STATUS current
        DESCRIPTION
            "The table contains statistics information for interface queue buffer usage."
        ::= { hwXQoSBufferUsageStatisticsObjects 3 }

    hwXQoSBufferUsageQueueStatEntry OBJECT-TYPE
        SYNTAX HwXQoSBufferUsageQueueStatEntry
        MAX-ACCESS not-accessible
        STATUS current
        DESCRIPTION
            "Entries of interface queue buffer usage statistics table."
        INDEX { hwXQosBufferUsageQueueStatIfindex, hwXQosBufferUsageQueueStatQueueId }
        ::= { hwXQoSBufferUsageQueueStatTable 1 }

    HwXQoSBufferUsageQueueStatEntry ::=
        SEQUENCE {
            hwXQosBufferUsageQueueStatIfindex
                Integer32,
            hwXQosBufferUsageQueueStatQueueId
                Integer32,
            hwXQosBufferUsageQueueStatTotalLength
                Counter64,
            hwXQosBufferUsageQueueStatUsedLength
                Counter64,
            hwXQosBufferUsageQueueStatRemainedLength
                Counter64,
            hwXQosBufferUsageQueueStatPeakUsedLength
                Counter64,
            hwXQosBufferUsageQueueStatAverageUsedLength
                Counter64
            }

    hwXQosBufferUsageQueueStatIfindex OBJECT-TYPE
        SYNTAX Integer32
        MAX-ACCESS not-accessible
        STATUS current
        DESCRIPTION
            "The interface index."
        ::= { hwXQoSBufferUsageQueueStatEntry 1 }

    hwXQosBufferUsageQueueStatQueueId OBJECT-TYPE
        SYNTAX Integer32 (0..7)
        MAX-ACCESS not-accessible
        STATUS current
        DESCRIPTION
            "The interface queue index.
                The value ranges from 0 to 7.
            "
        ::= { hwXQoSBufferUsageQueueStatEntry 2 }

    hwXQosBufferUsageQueueStatTotalLength OBJECT-TYPE
        SYNTAX Counter64
        MAX-ACCESS read-only
        STATUS current
        DESCRIPTION
            "The total kbyte number of interface queue buffer."
        ::= { hwXQoSBufferUsageQueueStatEntry 3 }

    hwXQosBufferUsageQueueStatUsedLength OBJECT-TYPE
        SYNTAX Counter64
        MAX-ACCESS read-only
        STATUS current
        DESCRIPTION
            "The used kbyte number of interface queue buffer."
        ::= { hwXQoSBufferUsageQueueStatEntry 4 }

    hwXQosBufferUsageQueueStatRemainedLength OBJECT-TYPE
        SYNTAX Counter64
        MAX-ACCESS read-only
        STATUS current
        DESCRIPTION
            "The remained kbyte number of interface queue buffer."
        ::= { hwXQoSBufferUsageQueueStatEntry 5 }

    hwXQosBufferUsageQueueStatPeakUsedLength OBJECT-TYPE
        SYNTAX Counter64
        MAX-ACCESS read-only
        STATUS current
        DESCRIPTION
            "The used kbyte number of interface queue buffer."
        ::= { hwXQoSBufferUsageQueueStatEntry 6 }

    hwXQosBufferUsageQueueStatAverageUsedLength OBJECT-TYPE
        SYNTAX Counter64
        MAX-ACCESS read-only
        STATUS current
        DESCRIPTION
            "The used kbyte number of interface queue buffer."
        ::= { hwXQoSBufferUsageQueueStatEntry 7 }

	hwXQoSEcnStatisticsObjects OBJECT IDENTIFIER ::= { hwXQoSStatisticsObjects 6 }
	-- ecn statistics
    hwXQoSEcnStatTable OBJECT-TYPE
        SYNTAX SEQUENCE OF HwXQoSEcnStatEntry
        MAX-ACCESS not-accessible
        STATUS current
        DESCRIPTION
            "The table contains statistics information for ecn."
        ::= { hwXQoSEcnStatisticsObjects 1 }
    hwXQoSEcnStatEntry OBJECT-TYPE
        SYNTAX HwXQoSEcnStatEntry
        MAX-ACCESS not-accessible
        STATUS current
        DESCRIPTION
            "Entries of ecn statistics table."
        INDEX { hwXQosEcnStatIfIndex, hwXQosEcnStatQueueId }
        ::= { hwXQoSEcnStatTable 1 }
    HwXQoSEcnStatEntry ::=
        SEQUENCE {
            hwXQosEcnStatIfIndex
                Integer32,
            hwXQosEcnStatQueueId
                Integer32,
            hwXQosEcnStatRemarkedPackets
                Counter64,
            hwXQosEcnStatRemarkedPacketsRate
                Counter64
            }
    hwXQosEcnStatIfIndex OBJECT-TYPE
        SYNTAX Integer32
        MAX-ACCESS not-accessible
        STATUS current
        DESCRIPTION
            "The index of the interface."
        ::= { hwXQoSEcnStatEntry 1 }
    hwXQosEcnStatQueueId OBJECT-TYPE
        SYNTAX Integer32 (0..8)
        MAX-ACCESS not-accessible
        STATUS current
        DESCRIPTION
            "The index of the interface queue.
                The value ranges from 0 to 8.
                queue id 8 indicate the whole interface."
        ::= { hwXQoSEcnStatEntry 2 }
    hwXQosEcnStatRemarkedPackets OBJECT-TYPE
        SYNTAX Counter64
        MAX-ACCESS read-only
        STATUS current
        DESCRIPTION
            "The ecn remarked packets."
        ::= { hwXQoSEcnStatEntry 3 }
    hwXQosEcnStatRemarkedPacketsRate OBJECT-TYPE
        SYNTAX Counter64
        MAX-ACCESS read-only
        STATUS current
        DESCRIPTION
            "The ecn remarked packets rate."
        ::= { hwXQoSEcnStatEntry 4 }
	
	hwXQoSPfcStatisticsObjects OBJECT IDENTIFIER ::= { hwXQoSStatisticsObjects 7 }
    -- pfc statistics
    hwXQoSPfcStatisticsTable OBJECT-TYPE
        SYNTAX SEQUENCE OF HwXQoSPfcStatisticsEntry
        MAX-ACCESS not-accessible
        STATUS current
        DESCRIPTION
            "A table of DCB PFC frame statistics for queues on the interface."
        ::= { hwXQoSPfcStatisticsObjects 1 }
    hwXQoSPfcStatisticsEntry OBJECT-TYPE
        SYNTAX HwXQoSPfcStatisticsEntry
        MAX-ACCESS not-accessible
        STATUS current
        DESCRIPTION
            "DCB PFC frame statistics entry."
        INDEX { hwXQoSPfcIfIndex, hwXQoSPfcQueueId }
        ::= { hwXQoSPfcStatisticsTable 1 }
    HwXQoSPfcStatisticsEntry ::=
        SEQUENCE {
            hwXQoSPfcIfIndex
                Integer32,
            hwXQoSPfcQueueId
                Integer32,
            hwXQoSPfcRxFrame
                Counter64,
            hwXQoSPfcTxFrame
                Counter64,
            hwXQoSPfcRxRate
                Counter64,
            hwXQoSPfcTxRate
                Counter64,
            hwXQoSPfcDeadlockNum
                Counter64,
            hwXQoSPfcRecoveryNum
                Counter64
            }
    hwXQoSPfcIfIndex OBJECT-TYPE
        SYNTAX Integer32
        MAX-ACCESS read-only
        STATUS current
        DESCRIPTION
            "The index of the interface."
        ::= { hwXQoSPfcStatisticsEntry 1 }
    hwXQoSPfcQueueId OBJECT-TYPE
        SYNTAX Integer32 (0..8)
        MAX-ACCESS read-only
        STATUS current
        DESCRIPTION
            "The index of the interface queue. The value ranges from 0 to 8. The index 8 indicates the whole interface."
        ::= { hwXQoSPfcStatisticsEntry 2 }
    hwXQoSPfcRxFrame OBJECT-TYPE
        SYNTAX Counter64
        MAX-ACCESS read-only
        STATUS current
        DESCRIPTION
            "The number of PFC frames received by the queue."
        ::= { hwXQoSPfcStatisticsEntry 3 }
    hwXQoSPfcTxFrame OBJECT-TYPE
        SYNTAX Counter64
        MAX-ACCESS read-only
        STATUS current
        DESCRIPTION
            "The number of PFC frames sent by the queue."
        ::= { hwXQoSPfcStatisticsEntry 4 }
    hwXQoSPfcRxRate OBJECT-TYPE
        SYNTAX Counter64
        MAX-ACCESS read-only
        STATUS current
        DESCRIPTION
            "The rate at which the queue receives PFC frames."
        ::= { hwXQoSPfcStatisticsEntry 5 }
    hwXQoSPfcTxRate OBJECT-TYPE
        SYNTAX Counter64
        MAX-ACCESS read-only
        STATUS current
        DESCRIPTION
            "The rate at which the queue sends PFC frames."
        ::= { hwXQoSPfcStatisticsEntry 6 }
    hwXQoSPfcDeadlockNum OBJECT-TYPE
        SYNTAX Counter64
        MAX-ACCESS read-only
        STATUS current
        DESCRIPTION
            "The number of detected PFC deadlocks."
        ::= { hwXQoSPfcStatisticsEntry 7 }
    hwXQoSPfcRecoveryNum OBJECT-TYPE
        SYNTAX Counter64
        MAX-ACCESS read-only
        STATUS current
        DESCRIPTION
            "The number of recovery times after PFC deadlocks occur."
        ::= { hwXQoSPfcStatisticsEntry 8 }

    hwXQoSPfcStatisticsResetTable OBJECT-TYPE
        SYNTAX SEQUENCE OF HwXQoSPfcStatisticsResetEntry
        MAX-ACCESS not-accessible
        STATUS current
        DESCRIPTION
            "Reset DCB PFC frame statistics."
        ::= { hwXQoSPfcStatisticsObjects 2 }
    hwXQoSPfcStatisticsResetEntry OBJECT-TYPE
        SYNTAX HwXQoSPfcStatisticsResetEntry
        MAX-ACCESS not-accessible
        STATUS current
        DESCRIPTION
            "The entry for clearing DCB PFC frame statistics on an interface."
        INDEX { hwXQoSPfcResetIfIndex }
        ::= { hwXQoSPfcStatisticsResetTable 1 }
    HwXQoSPfcStatisticsResetEntry ::=
        SEQUENCE {
            hwXQoSPfcResetIfIndex
                Integer32,
            hwXQoSPfcResetFlag
                ResetFlag
            }
    hwXQoSPfcResetIfIndex OBJECT-TYPE
        SYNTAX Integer32
        MAX-ACCESS read-only
        STATUS current
        DESCRIPTION
            "The index of the interface."
        ::= { hwXQoSPfcStatisticsResetEntry 1 }
    hwXQoSPfcResetFlag OBJECT-TYPE
        SYNTAX ResetFlag
        MAX-ACCESS read-write
        STATUS current
        DESCRIPTION
            "Reset DCB PFC frame statistics information."
        ::= { hwXQoSPfcStatisticsResetEntry 2 }

    -- 1.3.6.1.4.1.2011.5.25.32.4.1.5
    hwXQoSGlobalObjects OBJECT IDENTIFIER ::= { hwXQoSObjects 5 }

    -- 1.3.6.1.4.1.2011.5.25.32.4.1.5.1
    hwXQoSSoftCarCfgTable OBJECT-TYPE
        SYNTAX SEQUENCE OF HwXQoSSoftCarCfgEntry
        MAX-ACCESS not-accessible
        STATUS current
        DESCRIPTION
            "A table of software CAR  configuration information."
        ::= { hwXQoSGlobalObjects 1 }

    -- 1.3.6.1.4.1.2011.5.25.32.4.1.5.1.1
    hwXQoSSoftCarCfgEntry OBJECT-TYPE
        SYNTAX HwXQoSSoftCarCfgEntry
        MAX-ACCESS not-accessible
        STATUS current
        DESCRIPTION
            "Software CAR configuration information entry."
        INDEX { hwXQoSSoftCarIndex }
        ::= { hwXQoSSoftCarCfgTable 1 }

    HwXQoSSoftCarCfgEntry ::=
        SEQUENCE {
            hwXQoSSoftCarIndex
                Integer32,
            hwXQoSSoftCarName
                OCTET STRING,
            hwXQoSSoftCarCir
                Integer32,
            hwXQoSSoftCarCbs
                Integer32,
            hwXQoSSoftCarRowStatus
                RowStatus
         }

    -- 1.3.6.1.4.1.2011.5.25.32.4.1.5.1.1.1
    hwXQoSSoftCarIndex OBJECT-TYPE
        SYNTAX Integer32 (0..65534)
        MAX-ACCESS not-accessible
        STATUS current
        DESCRIPTION
            "Index of software car."
        ::= { hwXQoSSoftCarCfgEntry 1 }

    -- 1.3.6.1.4.1.2011.5.25.32.4.1.5.1.1.2
    hwXQoSSoftCarName OBJECT-TYPE
        SYNTAX OCTET STRING (SIZE (1..31))
        MAX-ACCESS read-create
        STATUS current
        DESCRIPTION
            "Software car name."
        ::= { hwXQoSSoftCarCfgEntry 2 }

    -- 1.3.6.1.4.1.2011.5.25.32.4.1.5.1.1.3
    hwXQoSSoftCarCir OBJECT-TYPE
        SYNTAX Integer32
        MAX-ACCESS read-create
        STATUS current
        DESCRIPTION
            "Committed Information Rate. Unit: kbps."
        ::= { hwXQoSSoftCarCfgEntry 3 }

    -- 1.3.6.1.4.1.2011.5.25.32.4.1.5.1.1.4
    hwXQoSSoftCarCbs OBJECT-TYPE
        SYNTAX Integer32
        MAX-ACCESS read-create
        STATUS current
        DESCRIPTION
            "Committed Burst Size. Unit: byte"
        ::= { hwXQoSSoftCarCfgEntry 4 }

    -- 1.3.6.1.4.1.2011.5.25.32.4.1.5.1.1.5
    hwXQoSSoftCarRowStatus OBJECT-TYPE
        SYNTAX RowStatus
        MAX-ACCESS read-create
        STATUS current
        DESCRIPTION
            "RowStatus. Three actions are used: active,
            createAndGo, destroy."
        ::= { hwXQoSSoftCarCfgEntry 5 }

    -- 1.3.6.1.4.1.2011.5.25.32.4.1.5.2
    hwXQoSGlobalWredClassCfgTable OBJECT-TYPE
        SYNTAX SEQUENCE OF HwXQoSGlobalWredClassCfgEntry
        MAX-ACCESS not-accessible
        STATUS current
        DESCRIPTION
            "A table of class based Wred  configuration information."
        ::= { hwXQoSGlobalObjects 2 }

    -- 1.3.6.1.4.1.2011.5.25.32.4.1.5.2.1
    hwXQoSGlobalWredClassCfgEntry OBJECT-TYPE
        SYNTAX HwXQoSGlobalWredClassCfgEntry
        MAX-ACCESS not-accessible
        STATUS current
        DESCRIPTION
            "Class based Wred configuration information entry."
        INDEX { hwXQoSGlobalWredClassIndex }
        ::= { hwXQoSGlobalWredClassCfgTable 1 }

    HwXQoSGlobalWredClassCfgEntry ::=
        SEQUENCE {
            hwXQoSGlobalWredClassIndex
                Integer32,
            hwXQoSGlobalWredClassLowlimit
                Integer32,
            hwXQoSGlobalWredClassHighlimit
                Integer32,
            hwXQoSGlobalWredClassDiscardProbability
                Integer32,
            hwXQoSGlobalWredClassSetDefault
                Integer32
         }

    -- 1.3.6.1.4.1.2011.5.25.32.4.1.5.2.1.1
    hwXQoSGlobalWredClassIndex OBJECT-TYPE
        SYNTAX Integer32 (0..7)
        MAX-ACCESS not-accessible
        STATUS current
        DESCRIPTION
            "Index of wred class."
        ::= { hwXQoSGlobalWredClassCfgEntry 1 }

    -- 1.3.6.1.4.1.2011.5.25.32.4.1.5.2.1.2
    hwXQoSGlobalWredClassLowlimit OBJECT-TYPE
        SYNTAX Integer32
        MAX-ACCESS read-write
        STATUS current
        DESCRIPTION
            "The Wred Lowlimit."
        ::= { hwXQoSGlobalWredClassCfgEntry 2 }

    -- 1.3.6.1.4.1.2011.5.25.32.4.1.5.2.1.3
    hwXQoSGlobalWredClassHighlimit OBJECT-TYPE
        SYNTAX Integer32
        MAX-ACCESS read-write
        STATUS current
        DESCRIPTION
            "The Wred Highlimit."
        ::= { hwXQoSGlobalWredClassCfgEntry 3 }

    -- 1.3.6.1.4.1.2011.5.25.32.4.1.5.2.1.4
    hwXQoSGlobalWredClassDiscardProbability OBJECT-TYPE
        SYNTAX Integer32
        MAX-ACCESS read-write
        STATUS current
        DESCRIPTION
            "The Wred Discard Probability."
        ::= { hwXQoSGlobalWredClassCfgEntry 4 }

    -- 1.3.6.1.4.1.2011.5.25.32.4.1.5.2.1.5
    hwXQoSGlobalWredClassSetDefault OBJECT-TYPE
        SYNTAX Integer32 (0..1)
        MAX-ACCESS read-write
        STATUS current
        DESCRIPTION
            "This OID is used for setting the WRED class info to default.
            When you want to set the value to default, set this OID to 1.
            "
        ::= { hwXQoSGlobalWredClassCfgEntry 5 }

    -- 1.3.6.1.4.1.2011.5.25.32.4.1.5.3
    hwXQoSGlobalWredTypeCfgTable OBJECT-TYPE
        SYNTAX SEQUENCE OF HwXQoSGlobalWredTypeCfgEntry
        MAX-ACCESS not-accessible
        STATUS current
        DESCRIPTION
            "A table of type based Wred  configuration information."
        ::= { hwXQoSGlobalObjects 3 }

    -- 1.3.6.1.4.1.2011.5.25.32.4.1.5.3.1
    hwXQoSGlobalWredTypeCfgEntry OBJECT-TYPE
        SYNTAX HwXQoSGlobalWredTypeCfgEntry
        MAX-ACCESS not-accessible
        STATUS current
        DESCRIPTION
            "Type based Wred  configuration information entry."
        INDEX { hwXQoSGlobalWredTypeIndex }
        ::= { hwXQoSGlobalWredTypeCfgTable 1 }

    HwXQoSGlobalWredTypeCfgEntry ::=
        SEQUENCE {
            hwXQoSGlobalWredTypeIndex
                Integer32,
            hwXQoSGlobalWredTypeName
                OCTET STRING,
            hwXQoSGlobalWredTypeLowlimit
                Integer32,
            hwXQoSGlobalWredTypeHighlimit
                Integer32,
            hwXQoSGlobalWredTypeDiscardProbability
                Integer32,
            hwXQoSGlobalWredTypeSetDefault
                Integer32
         }

    -- 1.3.6.1.4.1.2011.5.25.32.4.1.5.3.1.1
    hwXQoSGlobalWredTypeIndex OBJECT-TYPE
        SYNTAX Integer32 (0..3)
        MAX-ACCESS not-accessible
        STATUS current
        DESCRIPTION
            "Index of type."
        ::= { hwXQoSGlobalWredTypeCfgEntry 1 }

    -- 1.3.6.1.4.1.2011.5.25.32.4.1.5.3.1.2
    hwXQoSGlobalWredTypeName OBJECT-TYPE
        SYNTAX OCTET STRING (SIZE (1..31))
        MAX-ACCESS read-only
        STATUS current
        DESCRIPTION
            "Name of type."
        ::= { hwXQoSGlobalWredTypeCfgEntry 2 }

    -- 1.3.6.1.4.1.2011.5.25.32.4.1.5.3.1.3
    hwXQoSGlobalWredTypeLowlimit OBJECT-TYPE
        SYNTAX Integer32
        MAX-ACCESS read-write
        STATUS current
        DESCRIPTION
            "The Wred Lowlimit."
        ::= { hwXQoSGlobalWredTypeCfgEntry 3 }

    -- 1.3.6.1.4.1.2011.5.25.32.4.1.5.3.1.4
    hwXQoSGlobalWredTypeHighlimit OBJECT-TYPE
        SYNTAX Integer32
        MAX-ACCESS read-write
        STATUS current
        DESCRIPTION
            "The Wred Highlimit."
        ::= { hwXQoSGlobalWredTypeCfgEntry 4 }

    -- 1.3.6.1.4.1.2011.5.25.32.4.1.5.3.1.5
    hwXQoSGlobalWredTypeDiscardProbability OBJECT-TYPE
        SYNTAX Integer32
        MAX-ACCESS read-write
        STATUS current
        DESCRIPTION
            "The Wred Discard Probability."
        ::= { hwXQoSGlobalWredTypeCfgEntry 5 }

    -- 1.3.6.1.4.1.2011.5.25.32.4.1.5.3.1.6
    hwXQoSGlobalWredTypeSetDefault OBJECT-TYPE
        SYNTAX Integer32 (0..1)
        MAX-ACCESS read-write
        STATUS current
        DESCRIPTION
            "This OID is used for setting the WRED type info to default.
            When you want to set the value to default, set this OID to 1."
        ::= { hwXQoSGlobalWredTypeCfgEntry 6 }


    hwXQoSVlanBcastSuppressTable OBJECT-TYPE
        SYNTAX SEQUENCE OF HwXQoSVlanBcastSuppressEntry
        MAX-ACCESS not-accessible
        STATUS current
        DESCRIPTION
            "A table of VLAN broadcast suppression."
        ::= { hwXQoSGlobalObjects 4 }


    hwXQoSVlanBcastSuppressEntry OBJECT-TYPE
        SYNTAX HwXQoSVlanBcastSuppressEntry
        MAX-ACCESS not-accessible
        STATUS current
        DESCRIPTION
            "The entry of VLAN broadcast suppression."
        INDEX { hwXQoSVlanBcastSuppressVlanId }
        ::= { hwXQoSVlanBcastSuppressTable 1 }


    HwXQoSVlanBcastSuppressEntry ::=
        SEQUENCE {
            hwXQoSVlanBcastSuppressVlanId
                Integer32,
            hwXQoSVlanBcastSuppressValue
                Integer32,
            hwXQoSVlanBcastSuppressRowStatus
                RowStatus
         }

    hwXQoSVlanBcastSuppressVlanId OBJECT-TYPE
        SYNTAX Integer32 (1..4094)
        MAX-ACCESS not-accessible
        STATUS current
        DESCRIPTION
            "VLAN ID."
        ::= { hwXQoSVlanBcastSuppressEntry 1 }


    hwXQoSVlanBcastSuppressValue OBJECT-TYPE
        SYNTAX Integer32 (64..1000000)
        MAX-ACCESS read-create
        STATUS current
        DESCRIPTION
            "Suppression value for VLAN, unit KBPS."
        ::= { hwXQoSVlanBcastSuppressEntry 2 }


    hwXQoSVlanBcastSuppressRowStatus OBJECT-TYPE
        SYNTAX RowStatus
        MAX-ACCESS read-create
        STATUS current
        DESCRIPTION
            "Row status. Two actions are used: createAndGo, destroy"
        ::= { hwXQoSVlanBcastSuppressEntry 3 }
     hwXQoSScheduleProfileTable OBJECT-TYPE
        SYNTAX SEQUENCE OF HwXQoSScheduleProfileEntry
        MAX-ACCESS not-accessible
        STATUS current
        DESCRIPTION
            "A table of schedule profile."
        ::= { hwXQoSGlobalObjects 5 }


    hwXQoSScheduleProfileEntry OBJECT-TYPE
        SYNTAX HwXQoSScheduleProfileEntry
        MAX-ACCESS not-accessible
        STATUS current
        DESCRIPTION
            "The entry of schedule profile."
        INDEX { hwXQoSScheduleProfileName }
        ::= { hwXQoSScheduleProfileTable 1 }


    HwXQoSScheduleProfileEntry ::=
        SEQUENCE {
            hwXQoSScheduleProfileName
                OCTET STRING,
            hwXQoSScheduleQueueMode
                INTEGER,
            hwXQoSScheduleQueueBeWeight
                Integer32,
            hwXQoSScheduleQueueAf1Weight
                Integer32,
            hwXQoSScheduleQueueAf2Weight
                Integer32,
            hwXQoSScheduleQueueAf3Weight
                Integer32,
            hwXQoSScheduleQueueAf4Weight
                Integer32,
            hwXQoSScheduleQueueCs6Weight
                Integer32,
            hwXQoSScheduleQueueCs7Weight
                Integer32,
            hwXQoSScheduleQueueEfWeight
                Integer32,
            hwXQoSScheduleProfileRowStatus
                RowStatus
         }

    hwXQoSScheduleProfileName OBJECT-TYPE
            SYNTAX OCTET STRING (SIZE (1..31))
            MAX-ACCESS not-accessible
            STATUS current
            DESCRIPTION
                "The object specifies the schedule profile name."
            ::= { hwXQoSScheduleProfileEntry 1 }

    hwXQoSScheduleQueueMode OBJECT-TYPE
        SYNTAX INTEGER {
            pq(1),
            wrr(3),
            wfq(4),
            default(5),
            drr(6)
           }
        MAX-ACCESS read-write
        STATUS current
        DESCRIPTION
            "The Queue mode:
            pq(1),
            wrr(3),
            wfq(4),
            default(5),
            drr(6)
            "
        ::= { hwXQoSScheduleProfileEntry 2 }

    hwXQoSScheduleQueueBeWeight OBJECT-TYPE
        SYNTAX Integer32
        MAX-ACCESS read-write
        STATUS current
        DESCRIPTION
            "The be queue weight value when in wrr or drr queue mode."
        ::= { hwXQoSScheduleProfileEntry 3 }

    hwXQoSScheduleQueueAf1Weight OBJECT-TYPE
        SYNTAX Integer32
        MAX-ACCESS read-write
        STATUS current
        DESCRIPTION
            "The af1 queue weight value when in wrr or drr queue mode."
         ::= { hwXQoSScheduleProfileEntry 4 }

    hwXQoSScheduleQueueAf2Weight OBJECT-TYPE
        SYNTAX Integer32
        MAX-ACCESS read-write
        STATUS current
        DESCRIPTION
            "The af2 queue weight value when in wrr or drr queue mode."
        ::= { hwXQoSScheduleProfileEntry 5 }

    hwXQoSScheduleQueueAf3Weight OBJECT-TYPE
        SYNTAX Integer32
        MAX-ACCESS read-write
        STATUS current
        DESCRIPTION
            "The af3 queue weight value when in wrr or drr queue mode."
        ::= { hwXQoSScheduleProfileEntry 6 }

     hwXQoSScheduleQueueAf4Weight OBJECT-TYPE
        SYNTAX Integer32
        MAX-ACCESS read-write
        STATUS current
        DESCRIPTION
            "The af4 queue weight value when in wrr or drr queue mode."
        ::= { hwXQoSScheduleProfileEntry 7 }

    hwXQoSScheduleQueueCs6Weight OBJECT-TYPE
        SYNTAX Integer32
        MAX-ACCESS read-write
        STATUS current
        DESCRIPTION
            "The cs6 queue weight value when in wrr or drr queue mode."
        ::= { hwXQoSScheduleProfileEntry 8 }

     hwXQoSScheduleQueueCs7Weight OBJECT-TYPE
        SYNTAX Integer32
        MAX-ACCESS read-write
        STATUS current
        DESCRIPTION
            "The cs7 queue weight value when in wrr or drr queue mode."
        ::= { hwXQoSScheduleProfileEntry 9 }

     hwXQoSScheduleQueueEfWeight OBJECT-TYPE
        SYNTAX Integer32
        MAX-ACCESS read-write
        STATUS current
        DESCRIPTION
            "The ef queue weight value when in wrr or drr queue mode."
        ::= { hwXQoSScheduleProfileEntry 10 }

    hwXQoSScheduleProfileRowStatus OBJECT-TYPE
        SYNTAX RowStatus
        MAX-ACCESS read-create
        STATUS current
        DESCRIPTION
            "Row status. Two actions are used: createAndGo, destroy"
        ::= { hwXQoSScheduleProfileEntry 51 }

 -- ******************************************************************

--     ******************************************************************
--
-- hwXQosCarResourceTable
--
-- ******************************************************************
    -- 1.3.6.1.4.1.2011.5.25.32.4.1.5.6
    hwXQosCarResourceTable OBJECT-TYPE
        SYNTAX SEQUENCE OF HwXQosCarResourceEntry
        MAX-ACCESS not-accessible
        STATUS current
        DESCRIPTION
            "This table is used to query the CAR resource usage of board."
        ::= { hwXQoSGlobalObjects 6 }

    -- 1.3.6.1.4.1.2011.5.25.32.4.1.5.6.1
    hwXQosCarResourceEntry OBJECT-TYPE
        SYNTAX HwXQosCarResourceEntry
        MAX-ACCESS not-accessible
        STATUS current
        DESCRIPTION
            "hwXQosCarResourceEntry "
            INDEX { hwXQosCarResourceDirection, hwXQosCarResourceSlotNumber,hwXQosCarResourceServiceType}
        ::= { hwXQosCarResourceTable 1 }

    HwXQosCarResourceEntry ::=
        SEQUENCE {
            hwXQosCarResourceDirection
                INTEGER,
            hwXQosCarResourceSlotNumber
                Integer32,
            hwXQosCarResourceServiceType
                INTEGER,
            hwXQosCarResourceTotalValue
                Integer32,
            hwXQosCarResourceAllocatedValue
                Integer32,
            hwXQosCarResourceFreeValue
                Integer32
        }

    -- 1.3.6.1.4.1.2011.5.25.32.4.1.5.6.1.1
    hwXQosCarResourceDirection OBJECT-TYPE
        SYNTAX INTEGER
            {
            inbound(1),
            outbound(2)
            }
        MAX-ACCESS read-only
        STATUS current
        DESCRIPTION
            "The value of this object identifies the number of car resource on which direction."
        ::= { hwXQosCarResourceEntry 1 }

    -- 1.3.6.1.4.1.2011.5.25.32.4.1.5.6.1.2
    hwXQosCarResourceSlotNumber OBJECT-TYPE
        SYNTAX Integer32 (0..128)
        MAX-ACCESS read-only
        STATUS current
        DESCRIPTION
           "The value of this object identifies the number of car resource on which slot "
        ::= { hwXQosCarResourceEntry 2 }

    -- 1.3.6.1.4.1.2011.5.25.32.4.1.5.6.1.3
    hwXQosCarResourceServiceType OBJECT-TYPE
        SYNTAX INTEGER
        {
            acl(1),
            interface(2),
            family(3),
            user(4),
            daa(5),
            suppress(6),
            qosProfileSuppress(7),
            aclSuppress(8),
            familynp0(9),
            familynp1(10),
            familynp2(11),
            familynp3(12),
            usernp0(13),
            usernp1(14),
            usernp2(15),
            usernp3(16)
        }
        MAX-ACCESS read-only
        STATUS current
        DESCRIPTION
           "Service type:
            ACL      (1),
            INTERFACE(2),
            FAMILY   (3),
            USER     (4),
            DAA      (5),
            SUPPRESS (6),
            QOSPROFILE SUPPRESS(7),
            ACL SUPPRESS(8),
            FAMILY NP0(9),
            FAMILY NP1(10),
            FAMILY NP2(11),
            FAMILY NP3(12),
            USER NP0(13),
            USER NP1(14),
            USER NP2(15),
            USER NP3(16)"
        ::= { hwXQosCarResourceEntry 3 }

    -- 1.3.6.1.4.1.2011.5.25.32.4.1.5.6.1.4
    hwXQosCarResourceTotalValue OBJECT-TYPE
        SYNTAX Integer32 (0..2147483647)
        MAX-ACCESS read-only
        STATUS current
        DESCRIPTION
            "The number of the total car resource"
        ::= { hwXQosCarResourceEntry 4 }

    -- 1.3.6.1.4.1.2011.5.25.32.4.1.5.6.1.5
    hwXQosCarResourceAllocatedValue OBJECT-TYPE
        SYNTAX Integer32 (0..2147483647)
        MAX-ACCESS read-only
        STATUS current
        DESCRIPTION
           "The number of the used car resource "
        ::= { hwXQosCarResourceEntry 5 }

    -- 1.3.6.1.4.1.2011.5.25.32.4.1.5.6.1.6
    hwXQosCarResourceFreeValue OBJECT-TYPE
        SYNTAX Integer32 (0..2147483647)
        MAX-ACCESS read-only
        STATUS current
        DESCRIPTION
           "The number of the free car resource "
        ::= { hwXQosCarResourceEntry 6 }



--add by wangjing   2014/07/22
-- ******************************************************************
--
--    hwXQoSUserQueueResourceTable
--
-- ******************************************************************
       -- 1.3.6.1.4.1.2011.5.25.32.4.1.5.7
    hwXQoSUserQueueResourceTable OBJECT-TYPE
        SYNTAX      SEQUENCE OF HwXQoSUserQueueResourceEntry
        MAX-ACCESS  not-accessible
        STATUS      current
        DESCRIPTION
            " This table is used to collect statistics on user queue information. "
        ::= { hwXQoSGlobalObjects 7 }

    -- 1.3.6.1.4.1.2011.5.25.32.4.1.5.7.1
    hwXQoSUserQueueResourceEntry OBJECT-TYPE
        SYNTAX HwXQoSUserQueueResourceEntry
        MAX-ACCESS not-accessible
        STATUS current
        DESCRIPTION
            " hwXQoSUserQueueResourceEntry. "
        INDEX  { hwXQoSUserQueueResSlotID, hwXQoSUserQueueResDirection, hwXQoSUserQueueResPoolIndex}
        ::= { hwXQoSUserQueueResourceTable 1 }

    HwXQoSUserQueueResourceEntry ::=
    SEQUENCE {
            hwXQoSUserQueueResSlotID
                Unsigned32,
            hwXQoSUserQueueResDirection
                INTEGER,
            hwXQoSUserQueueResPoolIndex
                INTEGER,
            hwXQoSUserQueueResUsedNumber
                Unsigned32,
            hwXQoSUserQueueResFreeNumber
                Unsigned32,
            hwXQoSUserQueueResTotalNumber
                Unsigned32,
            hwXQosUserQueueResUsedCirBand
                Unsigned32,
            hwXQosUserQueueResFreeCirBand
                Unsigned32,
            hwXQosUserQueueResTotalCirBand
                Unsigned32,
            hwXQosUserQueueResUsedPirBand
                Unsigned32,
            hwXQosUserQueueResFreePirBand
                Unsigned32,
            hwXQosUserQueueResTotalPirBand
                Unsigned32,
            hwXQoSUserQueueResIsSharedResource
                Unsigned32
            }

    -- 1.3.6.1.4.1.2011.5.25.32.4.1.5.7.1.1
    hwXQoSUserQueueResSlotID  OBJECT-TYPE
        SYNTAX   Unsigned32 (1..128)
        MAX-ACCESS read-only
        STATUS current
        DESCRIPTION
        " This object indicates the slot ID of a user queue. "
        ::= { hwXQoSUserQueueResourceEntry 1 }

    -- 1.3.6.1.4.1.2011.5.25.32.4.1.5.7.1.2
    hwXQoSUserQueueResDirection  OBJECT-TYPE
        SYNTAX INTEGER
        {
        inbound(1),
        outbound(2)
        }
        MAX-ACCESS read-only
        STATUS current
        DESCRIPTION
        " This object indicates the direction of user-queue resource.
        The value can be:
        1: inbound
        2: outbound
        "
        ::= { hwXQoSUserQueueResourceEntry 2 }

    -- 1.3.6.1.4.1.2011.5.25.32.4.1.5.7.1.3
    hwXQoSUserQueueResPoolIndex OBJECT-TYPE
        SYNTAX  INTEGER
        {
            tm0(0),
            tm1(1),
            tm2(2),
            tm3(3),
            tmAll(4),
            etm0(5),
            etm1(6),
            etmAll(7),
            etm2(8),
            etm3(9),
            etm4(10),
            etm5(11),
            etm6(12),
            etm7(13),
            etm8(14),
            etm9(15),
            etm10(16),
            etm11(17),
            etm12(18),
            etm13(19),
            etm14(20),
            etm15(21),
            etm16(22),
            etm04queue(23),
            etm08queue(24),
            etm14queue(25),
            etm18queue(26),
            tm04queue(27),
            tm14queue(28),
            tm24queue(29),
            tm34queue(30),
            tm08queue(31),
            tm18queue(32),
            tm28queue(33),
            tm38queue(34),
            tm08queueenhance(35),
            tm18queueenhance(36),
            tm28queueenhance(37),
            tm38queueenhance(38),
            tm44queue(39),
            tm54queue(40),
            tm64queue(41),
            tm74queue(42),
            tm48queue(43),
            tm58queue(44),
            tm68queue(45),
            tm78queue(46),
            tm48queueenhance(47),
            tm58queueenhance(48),
            tm68queueenhance(49),
            tm78queueenhance(50),
            tm4(51),
            tm5(52),
            tm6(53),
            tm7(54)
        }
        MAX-ACCESS read-only
        STATUS current
        DESCRIPTION
            " This object indicates the index of user-queue resource pool.
            The value can be:
            0: tm-0
            1: tm-1
            2: tm-2
            3: tm-3
            4: tm-all
            5: etm-0
            6: etm-1
            7: etm-all
            8: etm-2
            9: etm-3
            10: etm-4
            11: etm-5
            12: etm-6
            13: etm-7
            14: etm-8
            15: etm-9
            16: etm-10
            17: etm-11
            18: etm-12
            19: etm-13
            20: etm-14
            21: etm-15
            22: etm-16
            23: etm04queue
            24: etm08queue
            25: etm14queue
            26: etm18queue
            27: tm04queue
            28: tm14queue
            29: tm24queue
            30: tm34queue
            31: tm08queue
            32: tm18queue
            33: tm28queue
            34: tm38queue
            35: tm08queueenhance
            36: tm18queueenhance
            37: tm28queueenhance
            38: tm38queueenhance
            39: tm44queue
            40: tm54queue
            41: tm64queue
            42: tm74queue
            43: tm48queue
            44: tm58queue
            45: tm68queue
            46: tm78queue
            47: tm48queueenhance
            48: tm58queueenhance
            49: tm68queueenhance
            50: tm78queueenhance
            51: tm-4
            52: tm-5
            53: tm-6
            54: tm-7
            "
        ::= { hwXQoSUserQueueResourceEntry 3 }

    -- 1.3.6.1.4.1.2011.5.25.32.4.1.5.7.1.4
    hwXQoSUserQueueResUsedNumber OBJECT-TYPE
        SYNTAX  Unsigned32
        MAX-ACCESS read-only
        STATUS current
        DESCRIPTION
            " This object indicates the used number of user-queue. "
        ::= { hwXQoSUserQueueResourceEntry 4 }

    -- 1.3.6.1.4.1.2011.5.25.32.4.1.5.7.1.5
    hwXQoSUserQueueResFreeNumber OBJECT-TYPE
        SYNTAX  Unsigned32
        MAX-ACCESS read-only
        STATUS current
        DESCRIPTION
            " This object indicates the number of idle user queue resources."
        ::= { hwXQoSUserQueueResourceEntry 5 }


    -- 1.3.6.1.4.1.2011.5.25.32.4.1.5.7.1.6
    hwXQoSUserQueueResTotalNumber OBJECT-TYPE
        SYNTAX  Unsigned32
        MAX-ACCESS read-only
        STATUS current
        DESCRIPTION
            " This object indicates the total number of user-queue. "
        ::= { hwXQoSUserQueueResourceEntry 6 }

    -- 1.3.6.1.4.1.2011.5.25.32.4.1.5.7.1.7
    hwXQosUserQueueResUsedCirBand OBJECT-TYPE
        SYNTAX  Unsigned32
        MAX-ACCESS read-only
        STATUS current
        DESCRIPTION
            " This object indicates the number of used CIR bandwidth resources. "
        ::= { hwXQoSUserQueueResourceEntry 7 }

    -- 1.3.6.1.4.1.2011.5.25.32.4.1.5.7.1.8
    hwXQosUserQueueResFreeCirBand OBJECT-TYPE
        SYNTAX  Unsigned32
        MAX-ACCESS read-only
        STATUS current
        DESCRIPTION
            " This object indicates the free cir bandwidth of user-queue. "
        ::= { hwXQoSUserQueueResourceEntry 8 }

    -- 1.3.6.1.4.1.2011.5.25.32.4.1.5.7.1.9
    hwXQosUserQueueResTotalCirBand OBJECT-TYPE
        SYNTAX  Unsigned32
        MAX-ACCESS read-only
        STATUS current
        DESCRIPTION
            " This object indicates the total number of CIR bandwidth resources. "
        ::= { hwXQoSUserQueueResourceEntry 9 }

    -- 1.3.6.1.4.1.2011.5.25.32.4.1.5.7.1.10
    hwXQosUserQueueResUsedPirBand OBJECT-TYPE
        SYNTAX  Unsigned32
        MAX-ACCESS read-only
        STATUS current
        DESCRIPTION
            " This object indicates the used pir bandwidth of user-queue. "
        ::= { hwXQoSUserQueueResourceEntry 10 }

    -- 1.3.6.1.4.1.2011.5.25.32.4.1.5.7.1.11
    hwXQosUserQueueResFreePirBand OBJECT-TYPE
        SYNTAX  Unsigned32
        MAX-ACCESS read-only
        STATUS current
        DESCRIPTION
            " This object indicates the number of idle PIR resources. "
        ::= { hwXQoSUserQueueResourceEntry 11 }

    -- 1.3.6.1.4.1.2011.5.25.32.4.1.5.7.1.12
    hwXQosUserQueueResTotalPirBand OBJECT-TYPE
        SYNTAX  Unsigned32
        MAX-ACCESS read-only
        STATUS current
        DESCRIPTION
            " This object indicates the total pir bandwidth of user-queue. "
        ::= { hwXQoSUserQueueResourceEntry 12 }

    -- 1.3.6.1.4.1.2011.5.25.32.4.1.5.7.1.13
    hwXQoSUserQueueResIsSharedResource OBJECT-TYPE
        SYNTAX  Unsigned32 (0..1)
        MAX-ACCESS read-only
        STATUS current
        DESCRIPTION
            " This object indicates if resource is shared . 0:not shared; 1:shared. "
        ::= { hwXQoSUserQueueResourceEntry 13 }

-- ******************************************************************
--
--     hwXQoSUserGroupQueueResourceTable
--
-- ******************************************************************
    -- 1.3.6.1.4.1.2011.5.25.32.4.1.5.8
    hwXQoSUserGroupQueueResourceTable OBJECT-TYPE
        SYNTAX      SEQUENCE OF HwXQoSUserGroupQueueResourceEntry
        MAX-ACCESS  not-accessible
        STATUS      current
        DESCRIPTION
            " This table is used to collect statistics on user group queues. "
        ::= { hwXQoSGlobalObjects 8 }

    -- 1.3.6.1.4.1.2011.5.25.32.4.1.5.8.1
    hwXQoSUserGroupQueueResourceEntry OBJECT-TYPE
        SYNTAX HwXQoSUserGroupQueueResourceEntry
        MAX-ACCESS not-accessible
        STATUS current
        DESCRIPTION
            " HwXQoSUserGroupQueueResourceEntry. "
        INDEX  { hwXQoSUserGroupQueueResSlotID, hwXQoSUserGroupQueueResDirection, hwXQoSUserGroupQueueResPoolIndex}
        ::= { hwXQoSUserGroupQueueResourceTable 1 }

    HwXQoSUserGroupQueueResourceEntry ::=
        SEQUENCE {
            hwXQoSUserGroupQueueResSlotID
                Unsigned32,
            hwXQoSUserGroupQueueResDirection
                INTEGER,
            hwXQoSUserGroupQueueResPoolIndex
                INTEGER,
            hwXQoSUserGroupQueueResUsedNumber
                Unsigned32,
            hwXQoSUserGroupQueueResFreeNumber
                Unsigned32,
            hwXQoSUserGroupQueueResTotalNumber
                Unsigned32,
            hwXQoSUserGroupQueueResIsSharedResource
                Unsigned32
                }

    -- 1.3.6.1.4.1.2011.5.25.32.4.1.5.8.1.1
    hwXQoSUserGroupQueueResSlotID  OBJECT-TYPE
        SYNTAX   Unsigned32 (1..128)
        MAX-ACCESS read-only
        STATUS current
        DESCRIPTION
            " This object indicates the slot ID of a GQ. "
        ::= { hwXQoSUserGroupQueueResourceEntry 1 }

    -- 1.3.6.1.4.1.2011.5.25.32.4.1.5.8.1.2
    hwXQoSUserGroupQueueResDirection  OBJECT-TYPE
        SYNTAX INTEGER
        {
            inbound(1),
            outbound(2)
        }
        MAX-ACCESS read-only
        STATUS current
        DESCRIPTION
            " This object indicates the direction of user-group-queue resource.
            The value can be:
            1: inbound
            2: outbound
            "
        ::= { hwXQoSUserGroupQueueResourceEntry 2 }

    -- 1.3.6.1.4.1.2011.5.25.32.4.1.5.8.1.3
    hwXQoSUserGroupQueueResPoolIndex OBJECT-TYPE
        SYNTAX  INTEGER
        {
            tm0(0),
            tm1(1),
            tm2(2),
            tm3(3),
            tmAll(4),
            etm0(5),
            etm1(6),
            etmAll(7),
            etm2(8),
            etm3(9),
            etm4(10),
            etm5(11),
            etm6(12),
            etm7(13),
            etm8(14),
            etm9(15),
            etm10(16),
            etm11(17),
            etm12(18),
            etm13(19),
            etm14(20),
            etm15(21),
            etm16(22),
            tm4(23),
            tm5(24),
            tm6(25),
            tm7(26)
        }
        MAX-ACCESS read-only
        STATUS current
        DESCRIPTION
            " This object indicates the index of user-group-queue resource pool.
            The value can be:
            0: tm-0
            1: tm-1
            2: tm-2
            3: tm-3
            4: tm-all
            5: etm-0
            6: etm-1
            7: etm-all
            8: etm-2
            9: etm-3
            10: etm-4
            11: etm-5
            12: etm-6
            13: etm-7
            14: etm-8
            15: etm-9
            16: etm-10
            17: etm-11
            18: etm-12
            19: etm-13
            20: etm-14
            21: etm-15
            22: etm-16
            23: tm-4
            24: tm-5
            25: tm-6
            26: tm-7
            "
        ::= { hwXQoSUserGroupQueueResourceEntry 3 }

    -- 1.3.6.1.4.1.2011.5.25.32.4.1.5.8.1.4
    hwXQoSUserGroupQueueResUsedNumber OBJECT-TYPE
        SYNTAX  Unsigned32
        MAX-ACCESS read-only
        STATUS current
        DESCRIPTION
            " This object indicates the number of used user queue resources. "
        ::= { hwXQoSUserGroupQueueResourceEntry 4 }

    -- 1.3.6.1.4.1.2011.5.25.32.4.1.5.8.1.5
    hwXQoSUserGroupQueueResFreeNumber OBJECT-TYPE
        SYNTAX  Unsigned32
        MAX-ACCESS read-only
        STATUS current
        DESCRIPTION
            " This object indicates the number of idle user queue resources."
        ::= { hwXQoSUserGroupQueueResourceEntry 5 }


    -- 1.3.6.1.4.1.2011.5.25.32.4.1.5.8.1.6
    hwXQoSUserGroupQueueResTotalNumber OBJECT-TYPE
        SYNTAX  Unsigned32
        MAX-ACCESS read-only
        STATUS current
        DESCRIPTION
            " This object indicates the total number of user queues. "
        ::= { hwXQoSUserGroupQueueResourceEntry 6 }

    -- 1.3.6.1.4.1.2011.5.25.32.4.1.5.8.1.7
    hwXQoSUserGroupQueueResIsSharedResource OBJECT-TYPE
        SYNTAX  Unsigned32 (0..1)
        MAX-ACCESS read-only
        STATUS current
        DESCRIPTION
            " This object indicates the upstream and downstream sharing flag of GQ resources.
                0: not shared. In shared mode, the GQ resource pool does not distinguish upstream and downstream traffic.
                1: shared. In non-sharing mode, the upstream and downstream resource pools are distinguished. "
        ::= { hwXQoSUserGroupQueueResourceEntry 7 }

-- ******************************************************************
--
--      hwXQoSSubPortQueueResourceTable
--
-- ******************************************************************
       -- 1.3.6.1.4.1.2011.5.25.32.4.1.5.9
        hwXQoSSubPortQueueResourceTable OBJECT-TYPE
          SYNTAX      SEQUENCE OF HwXQoSSubPortQueueResourceEntry
          MAX-ACCESS  not-accessible
          STATUS      current
          DESCRIPTION
              " This table is used to collect statistics on sub-interface queues.  "
          ::= { hwXQoSGlobalObjects 9 }

      -- 1.3.6.1.4.1.2011.5.25.32.4.1.5.9.1
      hwXQoSSubPortQueueResourceEntry OBJECT-TYPE
          SYNTAX HwXQoSSubPortQueueResourceEntry
          MAX-ACCESS not-accessible
          STATUS current
          DESCRIPTION
              " hwXQoSSubPortQueueResourceEntry. "
          INDEX  { hwXQoSSubPortQueueResSlotID, hwXQoSSubPortQueueResDirection, hwXQoSSubPortQueueResPoolIndex}
          ::= { hwXQoSSubPortQueueResourceTable 1 }

      HwXQoSSubPortQueueResourceEntry ::=
        SEQUENCE {
                hwXQoSSubPortQueueResSlotID
                    Unsigned32,
                hwXQoSSubPortQueueResDirection
                    INTEGER,
                hwXQoSSubPortQueueResPoolIndex
                    INTEGER,
                hwXQoSSubPortQueueResUsedNumber
                    Unsigned32,
                hwXQoSSubPortQueueResFreeNumber
                    Unsigned32,
                hwXQoSSubPortQueueResTotalNumber
                    Unsigned32
                }

      -- 1.3.6.1.4.1.2011.5.25.32.4.1.5.9.1.1
      hwXQoSSubPortQueueResSlotID  OBJECT-TYPE
            SYNTAX   Unsigned32 (1..128)
            MAX-ACCESS read-only
            STATUS current
            DESCRIPTION
            "This object indicates the slot ID of a sub-interface queue. "
            ::= { hwXQoSSubPortQueueResourceEntry 1 }

      -- 1.3.6.1.4.1.2011.5.25.32.4.1.5.9.1.2
      hwXQoSSubPortQueueResDirection  OBJECT-TYPE
            SYNTAX INTEGER
            {
            inbound(1),
            outbound(2)
            }
            MAX-ACCESS read-only
            STATUS current
            DESCRIPTION
            " This object indicates the direction of sub-port-queue resource.
            The value can be:
            1: inbound
            2: outbound
            "
            ::= { hwXQoSSubPortQueueResourceEntry 2 }

      -- 1.3.6.1.4.1.2011.5.25.32.4.1.5.9.1.3
      hwXQoSSubPortQueueResPoolIndex OBJECT-TYPE
            SYNTAX  INTEGER
            {
            tm0(0),
            tm1(1),
            tm2(2),
            tm3(3),
            tmAll(4),
            etm0(5),
            etm1(6),
            etmAll(7),
            etm2(8),
            etm3(9),
            etm4(10),
            etm5(11),
            etm6(12),
            etm7(13),
            etm8(14),
            etm9(15),
            etm10(16),
            etm11(17),
            etm12(18),
            etm13(19),
            etm14(20),
            etm15(21),
            etm16(22),
            tm4(23),
            tm5(24),
            tm6(25),
            tm7(26)
            }
            MAX-ACCESS read-only
            STATUS current
            DESCRIPTION
            " This object indicates the chip index.
              Value range:
              0: tm-0
              1: tm-1
              2: tm-2
              3: tm-3
              4: tm-all
              5: etm-0
              6: etm-1
              7: etm-all
              8: etm-2
              9: etm-3
             10: etm-4
             11: etm-5
             12: etm-6
             13: etm-7
             14: etm-8
             15: etm-9
             16: etm-10
             17: etm-11
             18: etm-12
             19: etm-13
             20: etm-14
             21: etm-15
             22: etm-16
             23: tm-4
             24: tm-5
             25: tm-6
             26: tm-7  "
            ::= { hwXQoSSubPortQueueResourceEntry 3 }

      -- 1.3.6.1.4.1.2011.5.25.32.4.1.5.9.1.4
      hwXQoSSubPortQueueResUsedNumber OBJECT-TYPE
            SYNTAX  Unsigned32
            MAX-ACCESS read-only
            STATUS current
            DESCRIPTION
            " This object indicates the used number of sub-port-queue. "
            ::= { hwXQoSSubPortQueueResourceEntry 4 }

      -- 1.3.6.1.4.1.2011.5.25.32.4.1.5.9.1.5
      hwXQoSSubPortQueueResFreeNumber OBJECT-TYPE
            SYNTAX  Unsigned32
            MAX-ACCESS read-only
            STATUS current
            DESCRIPTION
            " This object indicates the free number of sub-port-queue."
            ::= { hwXQoSSubPortQueueResourceEntry 5 }

      -- 1.3.6.1.4.1.2011.5.25.32.4.1.5.9.1.6
      hwXQoSSubPortQueueResTotalNumber OBJECT-TYPE
            SYNTAX  Unsigned32
            MAX-ACCESS read-only
            STATUS current
            DESCRIPTION
            " This object indicates the total number of user queues. "
            ::= { hwXQoSSubPortQueueResourceEntry 6 }

-- ******************************************************************
--
--       hwXQoSChannelResourceTable
--
-- ******************************************************************
    -- 1.3.6.1.4.1.2011.5.25.32.4.1.5.10
    hwXQoSChannelResourceTable OBJECT-TYPE
        SYNTAX      SEQUENCE OF HwXQoSChannelResourceEntry
        MAX-ACCESS  not-accessible
        STATUS      current
        DESCRIPTION
            "This table is used to query the usage of channel bandwidth on a chip. "
        ::= { hwXQoSGlobalObjects 10 }

    -- 1.3.6.1.4.1.2011.5.25.32.4.1.5.10.1
    hwXQoSChannelResourceEntry OBJECT-TYPE
        SYNTAX HwXQoSChannelResourceEntry
        MAX-ACCESS not-accessible
        STATUS current
        DESCRIPTION
            " hwXQoSChannelResourceEntry. "
        INDEX  { hwXQoSChannelResSlotID, hwXQoSChannelResPoolIndex, hwXQoSChannelResChannelID }
        ::= { hwXQoSChannelResourceTable 1 }

    HwXQoSChannelResourceEntry ::=
        SEQUENCE {
            hwXQoSChannelResSlotID
                Unsigned32,
            hwXQoSChannelResPoolIndex
                INTEGER,
            hwXQoSChannelResChannelID
                Unsigned32,
            hwXQoSChannelResChannelBand
                Unsigned32,
            hwXQoSChannelResUsedNumber
                Unsigned32,
            hwXQoSChannelResFreeNumber
                Unsigned32,
            hwXQoSChannelResTotalNumber
                Unsigned32,
            hwXQoSChannelResSuggestMaxNumber
                Unsigned32
                }

    -- 1.3.6.1.4.1.2011.5.25.32.4.1.5.10.1.1
    hwXQoSChannelResSlotID  OBJECT-TYPE
        SYNTAX   Unsigned32 (1..128)
        MAX-ACCESS read-only
        STATUS current
        DESCRIPTION
            " This object indicates the index of the interface on which banknote information is collected. "
        ::= { hwXQoSChannelResourceEntry 1 }

    -- 1.3.6.1.4.1.2011.5.25.32.4.1.5.10.1.2
    hwXQoSChannelResPoolIndex  OBJECT-TYPE
        SYNTAX INTEGER
        {
            tm0Pool0(0),
            tm0Pool1(1),
            tm1Pool0(2),
            tm1Pool1(3)
        }
        MAX-ACCESS read-only
        STATUS current
        DESCRIPTION
            " This object indicates the index of user-queue channel resource pool.
            The value can be:
            0: tm0-pool0
            1: tm0-pool1
            2: tm1-pool0
            3: tm1-pool1
            "
        ::= { hwXQoSChannelResourceEntry 2 }

    -- 1.3.6.1.4.1.2011.5.25.32.4.1.5.10.1.3
    hwXQoSChannelResChannelID OBJECT-TYPE
        SYNTAX  Unsigned32 (0..16)
        MAX-ACCESS read-only
        STATUS current
        DESCRIPTION
            " This object indicates the index of the banknote channel resource."
        ::= { hwXQoSChannelResourceEntry 3 }

    -- 1.3.6.1.4.1.2011.5.25.32.4.1.5.10.1.4
    hwXQoSChannelResChannelBand OBJECT-TYPE
        SYNTAX  Unsigned32
        MAX-ACCESS read-only
        STATUS current
        DESCRIPTION
            " This object indicates the actual channel bandwidth of user-queue channel. "
        ::= { hwXQoSChannelResourceEntry 4 }

    -- 1.3.6.1.4.1.2011.5.25.32.4.1.5.10.1.5
    hwXQoSChannelResUsedNumber OBJECT-TYPE
        SYNTAX  Unsigned32
        MAX-ACCESS read-only
        STATUS current
        DESCRIPTION
            " This object indicates the number of used banknote channels."
        ::= { hwXQoSChannelResourceEntry 5 }


    -- 1.3.6.1.4.1.2011.5.25.32.4.1.5.10.1.6
    hwXQoSChannelResFreeNumber OBJECT-TYPE
        SYNTAX  Unsigned32
        MAX-ACCESS read-only
        STATUS current
        DESCRIPTION
            " This object indicates the free number of user-queue channel. "
        ::= { hwXQoSChannelResourceEntry 6 }

    -- 1.3.6.1.4.1.2011.5.25.32.4.1.5.10.1.7
    hwXQoSChannelResTotalNumber OBJECT-TYPE
        SYNTAX  Unsigned32
        MAX-ACCESS read-only
        STATUS current
        DESCRIPTION
            " This object indicates the total number of banknote channels. "
        ::= { hwXQoSChannelResourceEntry 7 }

    -- 1.3.6.1.4.1.2011.5.25.32.4.1.5.10.1.8
    hwXQoSChannelResSuggestMaxNumber OBJECT-TYPE
        SYNTAX  Unsigned32
        MAX-ACCESS read-only
        STATUS current
        DESCRIPTION
            " This object indicates the suggest max number of user-queue channel. "
        ::= { hwXQoSChannelResourceEntry 8 }


-- ******************************************************************
--
--         hwXQoSTemplateResourceTable
--
-- ******************************************************************
    -- 1.3.6.1.4.1.2011.5.25.32.4.1.5.11
    hwXQoSTemplateResourceTable OBJECT-TYPE
        SYNTAX      SEQUENCE OF HwXQoSTemplateResourceEntry
        MAX-ACCESS  not-accessible
        STATUS      current
        DESCRIPTION
            " This table describes the configuration template information of a traffic policy, traffic classifier, traffic behavior, and QoS profile. "
        ::= { hwXQoSGlobalObjects 11 }

    -- 1.3.6.1.4.1.2011.5.25.32.4.1.5.11.1
    hwXQoSTemplateResourceEntry OBJECT-TYPE
        SYNTAX HwXQoSTemplateResourceEntry
        MAX-ACCESS not-accessible
        STATUS current
        DESCRIPTION
            " hwXQoSTemplateResourceEntry. "
        INDEX  { hwXQoSTemplateResType }
        ::= { hwXQoSTemplateResourceTable 1 }

    HwXQoSTemplateResourceEntry ::=
        SEQUENCE {
            hwXQoSTemplateResType
                INTEGER,
            hwXQoSTemplateResUsedNumber
                Unsigned32,
            hwXQoSTemplateResFreeNumber
                Unsigned32,
            hwXQoSTemplateResTotalNumber
                Unsigned32
            }

    -- 1.3.6.1.4.1.2011.5.25.32.4.1.5.11.1.1
    hwXQoSTemplateResType  OBJECT-TYPE
        SYNTAX   INTEGER
        {
            trafficPolicy(0),
            trafficClassifier(1),
            trafficBehavior(2),
            qosProfile(3),
            flowQueue(4)
        }
        MAX-ACCESS read-only
        STATUS current
        DESCRIPTION
            " This object indicates the type of template resource.
            The value can be:
            0: traffic-policy
            1: traffic-classifier
            2: traffic-behavior
            3: qos-profile
            4: flow-queue
            "
        ::= { hwXQoSTemplateResourceEntry 1 }

    -- 1.3.6.1.4.1.2011.5.25.32.4.1.5.11.1.2
    hwXQoSTemplateResUsedNumber  OBJECT-TYPE
        SYNTAX Unsigned32
        MAX-ACCESS read-only
        STATUS current
        DESCRIPTION
            " This object indicates the number of used configuration profiles.  "
        ::= { hwXQoSTemplateResourceEntry 2 }

    -- 1.3.6.1.4.1.2011.5.25.32.4.1.5.11.1.3
    hwXQoSTemplateResFreeNumber OBJECT-TYPE
        SYNTAX  Unsigned32
        MAX-ACCESS read-only
        STATUS current
        DESCRIPTION
            " This object indicates the free number of template resource "
        ::= { hwXQoSTemplateResourceEntry 3 }

    -- 1.3.6.1.4.1.2011.5.25.32.4.1.5.11.1.4
    hwXQoSTemplateResTotalNumber OBJECT-TYPE
        SYNTAX  Unsigned32
        MAX-ACCESS read-only
        STATUS current
        DESCRIPTION
            " This object indicates the total number of configuration profiles. "
        ::= { hwXQoSTemplateResourceEntry 4 }

-- ******************************************************************
--
--          hwXQoSCBPairResourceTable
--
-- ******************************************************************
    -- 1.3.6.1.4.1.2011.5.25.32.4.1.5.12
    hwXQoSCBPairResourceTable OBJECT-TYPE
        SYNTAX      SEQUENCE OF HwXQoSCBPairResourceEntry
        MAX-ACCESS  not-accessible
        STATUS      current
        DESCRIPTION
            " This table is used to query the configuration of Classifier-Behavior pairs in a traffic policy. "
        ::= { hwXQoSGlobalObjects 12 }

    -- 1.3.6.1.4.1.2011.5.25.32.4.1.5.12.1
    hwXQoSCBPairResourceEntry OBJECT-TYPE
        SYNTAX HwXQoSCBPairResourceEntry
        MAX-ACCESS not-accessible
        STATUS current
        DESCRIPTION
            " hwXQoSCBPairResourceEntry. "
        INDEX  { hwXQoSCBPairResTrafficPolicyName }
        ::= { hwXQoSCBPairResourceTable 1 }

    HwXQoSCBPairResourceEntry ::=
    SEQUENCE {
            hwXQoSCBPairResTrafficPolicyName
                OCTET STRING,
            hwXQoSCBPairResUsedNumber
                Unsigned32,
            hwXQoSCBPairResFreeNumber
                Unsigned32,
            hwXQoSCBPairResTotalNumber
                Unsigned32
            }

    -- 1.3.6.1.4.1.2011.5.25.32.4.1.5.12.1.1
    hwXQoSCBPairResTrafficPolicyName  OBJECT-TYPE
        SYNTAX OCTET STRING (SIZE (1..127))
        MAX-ACCESS read-only
        STATUS current
        DESCRIPTION
            " This object indicates the policy name corresponding to the Classifier-Behavior pair in the traffic policy."
        ::= { hwXQoSCBPairResourceEntry 1 }

    -- 1.3.6.1.4.1.2011.5.25.32.4.1.5.12.1.2
    hwXQoSCBPairResUsedNumber  OBJECT-TYPE
        SYNTAX Unsigned32
        MAX-ACCESS read-only
        STATUS current
        DESCRIPTION
            " This object indicates the configured cb-pair of the  traffic-policy. "
        ::= { hwXQoSCBPairResourceEntry 2 }

    -- 1.3.6.1.4.1.2011.5.25.32.4.1.5.12.1.3
    hwXQoSCBPairResFreeNumber OBJECT-TYPE
        SYNTAX  Unsigned32
        MAX-ACCESS read-only
        STATUS current
        DESCRIPTION
            " This object indicates the remainder cb-pair of the traffic-policy."
        ::= { hwXQoSCBPairResourceEntry 3 }

    -- 1.3.6.1.4.1.2011.5.25.32.4.1.5.12.1.4
    hwXQoSCBPairResTotalNumber OBJECT-TYPE
        SYNTAX  Unsigned32
        MAX-ACCESS read-only
        STATUS current
        DESCRIPTION
            " This object indicates the total number of Classifier-Behavior pairs that can be configured in a traffic policy. "
        ::= { hwXQoSCBPairResourceEntry 4 }

-- ******************************************************************
--
--           hwXQoSBindingTrafficPolicyResourceTable
--
-- ******************************************************************
    -- 1.3.6.1.4.1.2011.5.25.32.4.1.5.13
    hwXQoSBindingTrafficPolicyResourceTable OBJECT-TYPE
        SYNTAX      SEQUENCE OF HwXQoSBindingTrafficPolicyResourceEntry
        MAX-ACCESS  not-accessible
        STATUS      current
        DESCRIPTION
            "  This table describes information about traffic policies. "
        ::= { hwXQoSGlobalObjects 13 }

    -- 1.3.6.1.4.1.2011.5.25.32.4.1.5.13.1
    hwXQoSBindingTrafficPolicyResourceEntry OBJECT-TYPE
        SYNTAX HwXQoSBindingTrafficPolicyResourceEntry
        MAX-ACCESS not-accessible
        STATUS current
        DESCRIPTION
            " hwXQoSBindingTrafficPolicyResourceEntry. "
        INDEX  { hwXQoSBindingTrafficPolicyResSlotID }
        ::= {  hwXQoSBindingTrafficPolicyResourceTable 1 }

    HwXQoSBindingTrafficPolicyResourceEntry ::=
        SEQUENCE {
            hwXQoSBindingTrafficPolicyResSlotID
                Unsigned32,
            hwXQoSBindingTrafficPolicyResUsedNumber
                Unsigned32,
            hwXQoSBindingTrafficPolicyResFreeNumber
                Unsigned32,
            hwXQoSBindingTrafficPolicyResTotalNumber
                Unsigned32
            }

    -- 1.3.6.1.4.1.2011.5.25.32.4.1.5.13.1.1
    hwXQoSBindingTrafficPolicyResSlotID  OBJECT-TYPE
        SYNTAX Unsigned32 (1..128)
        MAX-ACCESS read-only
        STATUS current
        DESCRIPTION
            "This object indicates the ID of the board that is bound to a traffic policy instance. "
        ::= { hwXQoSBindingTrafficPolicyResourceEntry 1 }

    -- 1.3.6.1.4.1.2011.5.25.32.4.1.5.13.1.2
    hwXQoSBindingTrafficPolicyResUsedNumber  OBJECT-TYPE
        SYNTAX Unsigned32
        MAX-ACCESS read-only
        STATUS current
        DESCRIPTION
        "  This object indicates the applied traffic-policy number on this slot.   "
        ::= { hwXQoSBindingTrafficPolicyResourceEntry 2 }

    -- 1.3.6.1.4.1.2011.5.25.32.4.1.5.13.1.3
    hwXQoSBindingTrafficPolicyResFreeNumber OBJECT-TYPE
        SYNTAX  Unsigned32
        MAX-ACCESS read-only
        STATUS current
        DESCRIPTION
            " This object indicates the number of remaining traffic policy instances."
        ::= { hwXQoSBindingTrafficPolicyResourceEntry 3 }

    -- 1.3.6.1.4.1.2011.5.25.32.4.1.5.13.1.4
    hwXQoSBindingTrafficPolicyResTotalNumber OBJECT-TYPE
        SYNTAX  Unsigned32
        MAX-ACCESS read-only
        STATUS current
        DESCRIPTION
            " This object indicates the total number of instances that can be bound to a traffic policy. "
        ::= { hwXQoSBindingTrafficPolicyResourceEntry 4 }


-- ******************************************************************
--
--            hwXQoSAclTcamResourceTable
--
-- ******************************************************************
    -- 1.3.6.1.4.1.2011.5.25.32.4.1.5.14
    hwXQoSAclTcamResourceTable OBJECT-TYPE
        SYNTAX      SEQUENCE OF HwXQoSAclTcamResourceEntry
        MAX-ACCESS  not-accessible
        STATUS      current
        DESCRIPTION
            " This table is used to query the information about the chip used by an ACL. "
        ::= { hwXQoSGlobalObjects 14 }

    -- 1.3.6.1.4.1.2011.5.25.32.4.1.5.14.1
    hwXQoSAclTcamResourceEntry OBJECT-TYPE
        SYNTAX HwXQoSAclTcamResourceEntry
        MAX-ACCESS not-accessible
        STATUS current
        DESCRIPTION
            " hwXQoSAclTcamResourceEntry. "
        INDEX  { hwXQoSAclTcamResSlotID, hwXQoSAclTcamResAclType, hwXQoSAclTcamResPfeID }
        ::= {   hwXQoSAclTcamResourceTable 1 }

    HwXQoSAclTcamResourceEntry ::=
        SEQUENCE {
            hwXQoSAclTcamResSlotID
                Unsigned32,
            hwXQoSAclTcamResAclType
                INTEGER,
            hwXQoSAclTcamResPfeID
                INTEGER,
            hwXQoSAclTcamResUsedNumber
                Unsigned32,
            hwXQoSAclTcamResFreeNumber
                Unsigned32,
            hwXQoSAclTcamResTotalNumber
                Unsigned32,
            hwXQoSAclTcamResShareUsedNumber
                Unsigned32
            }

    -- 1.3.6.1.4.1.2011.5.25.32.4.1.5.14.1.1
    hwXQoSAclTcamResSlotID  OBJECT-TYPE
        SYNTAX Unsigned32 (1..128)
        MAX-ACCESS read-only
        STATUS current
        DESCRIPTION
            " This object indicates the slot-id of acl-tcam resource. "
        ::= { hwXQoSAclTcamResourceEntry 1 }

    -- 1.3.6.1.4.1.2011.5.25.32.4.1.5.14.1.2
    hwXQoSAclTcamResAclType  OBJECT-TYPE
        SYNTAX INTEGER
        {
            aclv4(0),
            aclv6(1),
            l2acl(2),
            mpls(3),
            uclv4(4),
            uclv6(5)
        }
        MAX-ACCESS read-only
        STATUS current
        DESCRIPTION
            " This object indicates the ACL type of the chip specification of rules.
                0: aclv4
                1: aclv6
                2: l2acl
                3: mpls
                4: uclv4
                5: uclv6
            "
        ::= { hwXQoSAclTcamResourceEntry 2 }

    -- 1.3.6.1.4.1.2011.5.25.32.4.1.5.14.1.3
    hwXQoSAclTcamResPfeID OBJECT-TYPE
        SYNTAX  INTEGER
        {
            pfe0(0),
            pfe1(1),
            pfe2(2),
            pfe3(3),
            pfe4(4),
            pfe5(5),
            pfe6(6),
            pfe7(7)
        }
        MAX-ACCESS read-only
        STATUS current
        DESCRIPTION
            " This object indicates the pfe-id of acl-tcam resource.
            The value can be:
                0: pfe-0
                1: pfe-1
            2: pfe-2
            3: pfe-3
            4: pfe-4
            5: pfe-5
            6: pfe-6
            7: pfe-7
            "
        ::= { hwXQoSAclTcamResourceEntry 3 }

    -- 1.3.6.1.4.1.2011.5.25.32.4.1.5.14.1.4
    hwXQoSAclTcamResUsedNumber OBJECT-TYPE
        SYNTAX  Unsigned32
        MAX-ACCESS read-only
        STATUS current
        DESCRIPTION
            " This object indicates the used number of acl-tcam resource. "
        ::= { hwXQoSAclTcamResourceEntry 4 }

    -- 1.3.6.1.4.1.2011.5.25.32.4.1.5.14.1.5
    hwXQoSAclTcamResFreeNumber OBJECT-TYPE
        SYNTAX  Unsigned32
        MAX-ACCESS read-only
        STATUS current
        DESCRIPTION
            " This object indicates the remaining number of chip specifications of rules. "
        ::= { hwXQoSAclTcamResourceEntry 5 }

    -- 1.3.6.1.4.1.2011.5.25.32.4.1.5.14.1.6
    hwXQoSAclTcamResTotalNumber OBJECT-TYPE
        SYNTAX  Unsigned32
        MAX-ACCESS read-only
        STATUS current
        DESCRIPTION
            " This object indicates the total number of acl-tcam resource. "
        ::= { hwXQoSAclTcamResourceEntry 6 }

    -- 1.3.6.1.4.1.2011.5.25.32.4.1.5.14.1.7
    hwXQoSAclTcamResShareUsedNumber OBJECT-TYPE
        SYNTAX  Unsigned32
        MAX-ACCESS read-only
        STATUS current
        DESCRIPTION
            "This object indicates the shared resources occupied by other services."
        ::= { hwXQoSAclTcamResourceEntry 7 }
-- end by wangjing

-- ******************************************************************

-- ******************************************************************
--
-- hwXQosBoardCarResourceTable
--
-- ******************************************************************
    -- 1.3.6.1.4.1.2011.5.25.32.4.1.5.15
    hwXQosBoardCarResourceTable OBJECT-TYPE
        SYNTAX SEQUENCE OF HwXQosBoardCarResourceEntry
        MAX-ACCESS not-accessible
        STATUS current
        DESCRIPTION
            "This table describes CAR resource information."
        ::= { hwXQoSGlobalObjects 15 }

    -- 1.3.6.1.4.1.2011.5.25.32.4.1.5.15.1
    hwXQosBoardCarResourceEntry OBJECT-TYPE
        SYNTAX HwXQosBoardCarResourceEntry
        MAX-ACCESS not-accessible
        STATUS current
        DESCRIPTION
            "hwXQosBoardCarResourceEntry "
            INDEX { hwXQosBoardCarResourceDirection, hwXQosBoardCarResourceSlotNumber,hwXQosBoardCarResourceType}
        ::= { hwXQosBoardCarResourceTable 1 }

    HwXQosBoardCarResourceEntry ::=
        SEQUENCE {
            hwXQosBoardCarResourceDirection
                INTEGER,
            hwXQosBoardCarResourceSlotNumber
                Integer32,
            hwXQosBoardCarResourceType
                INTEGER,
            hwXQosBoardCarResourceTotalValue
                Integer32,
            hwXQosBoardCarResourceAllocatedValue
                Integer32,
            hwXQosBoardCarResourceFreeValue
                Integer32
        }

    -- 1.3.6.1.4.1.2011.5.25.32.4.1.5.15.1.1
    hwXQosBoardCarResourceDirection OBJECT-TYPE
        SYNTAX INTEGER
            {
            inbound(1),
            outbound(2)
            }
        MAX-ACCESS read-only
        STATUS current
        DESCRIPTION
            "This object indicates the index of the interface direction where CAR resource statistics are collected."
        ::= { hwXQosBoardCarResourceEntry 1 }

    -- 1.3.6.1.4.1.2011.5.25.32.4.1.5.15.1.2
    hwXQosBoardCarResourceSlotNumber OBJECT-TYPE
        SYNTAX Integer32 (0..128)
        MAX-ACCESS read-only
        STATUS current
        DESCRIPTION
           "The value of this object identifies the number of board car resource on which slot "
        ::= { hwXQosBoardCarResourceEntry 2 }

    -- 1.3.6.1.4.1.2011.5.25.32.4.1.5.15.1.3
    hwXQosBoardCarResourceType OBJECT-TYPE
        SYNTAX INTEGER
        {
            cartype1(1),
            cartype4(2)
        }
        MAX-ACCESS read-only
        STATUS current
        DESCRIPTION
           "This object indicates the type of the CAR resource statistics."
        ::= { hwXQosBoardCarResourceEntry 3 }

    -- 1.3.6.1.4.1.2011.5.25.32.4.1.5.15.1.4
    hwXQosBoardCarResourceTotalValue OBJECT-TYPE
        SYNTAX Integer32 (0..2147483647)
        MAX-ACCESS read-only
        STATUS current
        DESCRIPTION
            "The number of the total board car resource"
        ::= { hwXQosBoardCarResourceEntry 4 }

    -- 1.3.6.1.4.1.2011.5.25.32.4.1.5.15.1.5
    hwXQosBoardCarResourceAllocatedValue OBJECT-TYPE
        SYNTAX Integer32 (0..2147483647)
        MAX-ACCESS read-only
        STATUS current
        DESCRIPTION
           "This object indicates the used CAR resources."
        ::= { hwXQosBoardCarResourceEntry 5 }

    -- 1.3.6.1.4.1.2011.5.25.32.4.1.5.15.1.6
    hwXQosBoardCarResourceFreeValue OBJECT-TYPE
        SYNTAX Integer32 (0..2147483647)
        MAX-ACCESS read-only
        STATUS current
        DESCRIPTION
           "The number of the free board car resource "
        ::= { hwXQosBoardCarResourceEntry 6 }

-- ******************************************************************
--
--     hwXQoSFlowWredResourceTable
--
-- ******************************************************************
    -- 1.3.6.1.4.1.2011.5.25.32.4.1.5.16
    hwXQoSFlowWredResourceTable OBJECT-TYPE
        SYNTAX      SEQUENCE OF HwXQoSFlowWredResourceEntry
        MAX-ACCESS  not-accessible
        STATUS      current
        DESCRIPTION
            " This table describes flow-wred resource information."
        ::= { hwXQoSGlobalObjects 16 }

    -- 1.3.6.1.4.1.2011.5.25.32.4.1.5.16.1
    hwXQoSFlowWredResourceEntry OBJECT-TYPE
        SYNTAX HwXQoSFlowWredResourceEntry
        MAX-ACCESS not-accessible
        STATUS current
        DESCRIPTION
            " hwXQoSFlowWredResourceEntry. "
        INDEX  { hwXQoSUserQueueResSlotID, hwXQoSUserQueueResDirection, hwXQoSUserQueueResPoolIndex}
        ::= { hwXQoSFlowWredResourceTable 1 }

    HwXQoSFlowWredResourceEntry ::=
        SEQUENCE {
            hwXQoSFlowWredResUsedNumber
                Unsigned32,
            hwXQoSFlowWredResFreeNumber
                Unsigned32,
            hwXQoSFlowWredResTotalNumber
                Unsigned32
            }

    -- 1.3.6.1.4.1.2011.5.25.32.4.1.5.16.1.4
    hwXQoSFlowWredResUsedNumber OBJECT-TYPE
        SYNTAX  Unsigned32
        MAX-ACCESS read-only
        STATUS current
        DESCRIPTION
            " This object indicates the number of used flow-wred resources. "
        ::= { hwXQoSFlowWredResourceEntry 4 }

    -- 1.3.6.1.4.1.2011.5.25.32.4.1.5.16.1.5
    hwXQoSFlowWredResFreeNumber OBJECT-TYPE
        SYNTAX  Unsigned32
        MAX-ACCESS read-only
        STATUS current
        DESCRIPTION
            " This object indicates the number of idle flow-wred resources."
        ::= { hwXQoSFlowWredResourceEntry 5 }

    -- 1.3.6.1.4.1.2011.5.25.32.4.1.5.16.1.6
    hwXQoSFlowWredResTotalNumber OBJECT-TYPE
        SYNTAX  Unsigned32
        MAX-ACCESS read-only
        STATUS current
        DESCRIPTION
            " This object indicates the total number of flow-wred resources. "
        ::= { hwXQoSFlowWredResourceEntry 6 }

-- ******************************************************************
--
--           hwXQoSBindingTrafficPolicyChassisResourceTable
--
-- ******************************************************************
    -- 1.3.6.1.4.1.2011.5.25.32.4.1.5.17
    hwXQoSBindingTrafficPolicyChassisResourceTable OBJECT-TYPE
        SYNTAX      SEQUENCE OF HwXQoSBindingTrafficPolicyChassisResourceEntry
        MAX-ACCESS  not-accessible
        STATUS      current
        DESCRIPTION
            " This table describes information about traffic policies. "
        ::= { hwXQoSGlobalObjects 17 }
    -- 1.3.6.1.4.1.2011.5.25.32.4.1.5.17.1
    hwXQoSBindingTrafficPolicyChassisResourceEntry OBJECT-TYPE
        SYNTAX HwXQoSBindingTrafficPolicyChassisResourceEntry
        MAX-ACCESS not-accessible
        STATUS current
        DESCRIPTION
            " hwXQoSBindingTrafficPolicyChassisResourceEntry. "
        INDEX  { hwXQoSBindingTrafficPolicyChassisResChassisID, hwXQoSBindingTrafficPolicyChassisResSlotID }
        ::= {  hwXQoSBindingTrafficPolicyChassisResourceTable 1 }
    HwXQoSBindingTrafficPolicyChassisResourceEntry ::=
        SEQUENCE {
            hwXQoSBindingTrafficPolicyChassisResChassisID
                Unsigned32,
            hwXQoSBindingTrafficPolicyChassisResSlotID
                Unsigned32,
            hwXQoSBindingTrafficPolicyChassisResUsedNumber
                Unsigned32,
            hwXQoSBindingTrafficPolicyChassisResFreeNumber
                Unsigned32,
            hwXQoSBindingTrafficPolicyChassisResTotalNumber
                Unsigned32
            }
    -- 1.3.6.1.4.1.2011.5.25.32.4.1.5.17.1.1
    hwXQoSBindingTrafficPolicyChassisResChassisID  OBJECT-TYPE
        SYNTAX Unsigned32 (1..16)
        MAX-ACCESS read-only
        STATUS current
        DESCRIPTION
        "This object indicates the ID of the Chassis that is bound to a traffic policy instance. "
        ::= { hwXQoSBindingTrafficPolicyChassisResourceEntry 1 }
    -- 1.3.6.1.4.1.2011.5.25.32.4.1.5.17.1.2
    hwXQoSBindingTrafficPolicyChassisResSlotID  OBJECT-TYPE
        SYNTAX Unsigned32 (1..128)
        MAX-ACCESS read-only
        STATUS current
        DESCRIPTION
        "This object indicates the ID of the board that is bound to a traffic policy instance. "
        ::= { hwXQoSBindingTrafficPolicyChassisResourceEntry 2 }
    -- 1.3.6.1.4.1.2011.5.25.32.4.1.5.17.1.3
    hwXQoSBindingTrafficPolicyChassisResUsedNumber  OBJECT-TYPE
        SYNTAX Unsigned32
        MAX-ACCESS read-only
        STATUS current
        DESCRIPTION
        "  This object indicates the applied traffic-policy number on the slot.   "
        ::= { hwXQoSBindingTrafficPolicyChassisResourceEntry 3 }
    -- 1.3.6.1.4.1.2011.5.25.32.4.1.5.17.1.4
    hwXQoSBindingTrafficPolicyChassisResFreeNumber OBJECT-TYPE
        SYNTAX  Unsigned32
        MAX-ACCESS read-only
        STATUS current
        DESCRIPTION
        " This object indicates the number of remaining traffic policy instances."
        ::= { hwXQoSBindingTrafficPolicyChassisResourceEntry 4 }
    -- 1.3.6.1.4.1.2011.5.25.32.4.1.5.17.1.5
    hwXQoSBindingTrafficPolicyChassisResTotalNumber OBJECT-TYPE
        SYNTAX  Unsigned32
        MAX-ACCESS read-only
        STATUS current
        DESCRIPTION
        " This object indicates the total number of instances that can be bound to a traffic policy. "
        ::= { hwXQoSBindingTrafficPolicyChassisResourceEntry 5 }
--BEGIN
    hwXQoSBindingTrafficPolicyBasicResourceTable OBJECT-TYPE
        SYNTAX      SEQUENCE OF HwXQoSBindingTrafficPolicyBasicResourceEntry
        MAX-ACCESS  not-accessible
        STATUS      current
        DESCRIPTION
            "  This table describes information about traffic policies. "
        ::= { hwXQoSGlobalObjects 18 }
 
    hwXQoSBindingTrafficPolicyBasicResourceEntry OBJECT-TYPE
        SYNTAX HwXQoSBindingTrafficPolicyBasicResourceEntry
        MAX-ACCESS not-accessible
        STATUS current
        DESCRIPTION
            " hwXQoSBindingTrafficPolicyBasicResourceEntry. "
        INDEX  { hwXQoSBindingTrafficPolicyBasicResSlotID }
        ::= {  hwXQoSBindingTrafficPolicyBasicResourceTable 1 }
 
    HwXQoSBindingTrafficPolicyBasicResourceEntry ::=
        SEQUENCE {
            hwXQoSBindingTrafficPolicyBasicResSlotID
                Unsigned32,
            hwXQoSBindingTrafficPolicyBasicResUsedNumber
                Unsigned32,
            hwXQoSBindingTrafficPolicyBasicResFreeNumber
                Unsigned32,
            hwXQoSBindingTrafficPolicyBasicResTotalNumber
                Unsigned32
            }
 
    hwXQoSBindingTrafficPolicyBasicResSlotID  OBJECT-TYPE
        SYNTAX Unsigned32 (1..128)
        MAX-ACCESS read-only
        STATUS current
        DESCRIPTION
            "This object indicates the ID of the board that is bound to a traffic policy instance. "
        ::= { hwXQoSBindingTrafficPolicyBasicResourceEntry 1 }
 
    hwXQoSBindingTrafficPolicyBasicResUsedNumber  OBJECT-TYPE
        SYNTAX Unsigned32
        MAX-ACCESS read-only
        STATUS current
        DESCRIPTION
        "  This object indicates the applied traffic-policy number on this slot.   "
        ::= { hwXQoSBindingTrafficPolicyBasicResourceEntry 2 }
 
    hwXQoSBindingTrafficPolicyBasicResFreeNumber OBJECT-TYPE
        SYNTAX  Unsigned32
        MAX-ACCESS read-only
        STATUS current
        DESCRIPTION
            " This object indicates the number of remaining traffic policy instances."
        ::= { hwXQoSBindingTrafficPolicyBasicResourceEntry 3 }
 
    hwXQoSBindingTrafficPolicyBasicResTotalNumber OBJECT-TYPE
        SYNTAX  Unsigned32
        MAX-ACCESS read-only
        STATUS current
        DESCRIPTION
            " This object indicates the total number of instances that can be bound to a traffic policy. "
        ::= { hwXQoSBindingTrafficPolicyBasicResourceEntry 4 }
--END
--BEGIN
    hwXQoSBindingTrafficPolicyChassisBasicResourceTable OBJECT-TYPE
        SYNTAX      SEQUENCE OF HwXQoSBindingTrafficPolicyChassisBasicResourceEntry
        MAX-ACCESS  not-accessible
        STATUS      current
        DESCRIPTION
            " This table describes information about traffic policies. "
        ::= { hwXQoSGlobalObjects 19 }
 
    hwXQoSBindingTrafficPolicyChassisBasicResourceEntry OBJECT-TYPE
        SYNTAX HwXQoSBindingTrafficPolicyChassisBasicResourceEntry
        MAX-ACCESS not-accessible
        STATUS current
        DESCRIPTION
            " hwXQoSBindingTrafficPolicyChassisBasicResourceEntry. "
        INDEX  { hwXQoSBindingTrafficPolicyChassisBasicResChassisID, hwXQoSBindingTrafficPolicyChassisBasicResSlotID }
        ::= {  hwXQoSBindingTrafficPolicyChassisBasicResourceTable 1 }
    HwXQoSBindingTrafficPolicyChassisBasicResourceEntry ::=
        SEQUENCE {
            hwXQoSBindingTrafficPolicyChassisBasicResChassisID
                Unsigned32,
            hwXQoSBindingTrafficPolicyChassisBasicResSlotID
                Unsigned32,
            hwXQoSBindingTrafficPolicyChassisBasicResUsedNumber
                Unsigned32,
            hwXQoSBindingTrafficPolicyChassisBasicResFreeNumber
                Unsigned32,
            hwXQoSBindingTrafficPolicyChassisBasicResTotalNumber
                Unsigned32
            }
 
    hwXQoSBindingTrafficPolicyChassisBasicResChassisID  OBJECT-TYPE
        SYNTAX Unsigned32 (1..16)
        MAX-ACCESS read-only
        STATUS current
        DESCRIPTION
        "This object indicates the ID of the Chassis that is bound to a traffic policy instance. "
        ::= { hwXQoSBindingTrafficPolicyChassisBasicResourceEntry 1 }
 
    hwXQoSBindingTrafficPolicyChassisBasicResSlotID  OBJECT-TYPE
        SYNTAX Unsigned32 (1..128)
        MAX-ACCESS read-only
        STATUS current
        DESCRIPTION
        "This object indicates the ID of the board that is bound to a traffic policy instance. "
        ::= { hwXQoSBindingTrafficPolicyChassisBasicResourceEntry 2 }
    -- 1.3.6.1.4.1.2011.5.25.32.4.1.5.17.1.3
    hwXQoSBindingTrafficPolicyChassisBasicResUsedNumber  OBJECT-TYPE
        SYNTAX Unsigned32
        MAX-ACCESS read-only
        STATUS current
        DESCRIPTION
        "  This object indicates the applied traffic-policy number on the slot.   "
        ::= { hwXQoSBindingTrafficPolicyChassisBasicResourceEntry 3 }
    -- 1.3.6.1.4.1.2011.5.25.32.4.1.5.17.1.4
    hwXQoSBindingTrafficPolicyChassisBasicResFreeNumber OBJECT-TYPE
        SYNTAX  Unsigned32
        MAX-ACCESS read-only
        STATUS current
        DESCRIPTION
        " This object indicates the number of remaining traffic policy instances."
        ::= { hwXQoSBindingTrafficPolicyChassisBasicResourceEntry 4 }
    -- 1.3.6.1.4.1.2011.5.25.32.4.1.5.17.1.5
    hwXQoSBindingTrafficPolicyChassisBasicResTotalNumber OBJECT-TYPE
        SYNTAX  Unsigned32
        MAX-ACCESS read-only
        STATUS current
        DESCRIPTION
        " This object indicates the total number of instances that can be bound to a traffic policy. "
        ::= { hwXQoSBindingTrafficPolicyChassisBasicResourceEntry 5 }
--END

  -- defend statistics
    hwXQoSCpDefendObjects OBJECT IDENTIFIER ::= { hwXQoSObjects 6 }

    hwXQoSCpDefendStatisticsTable OBJECT-TYPE
        SYNTAX SEQUENCE OF HwXQoSCpDefendStatisticsEntry
        MAX-ACCESS not-accessible
        STATUS current
        DESCRIPTION
            "A table of statistics on attack defense"
        ::= { hwXQoSCpDefendObjects 1 }

    hwXQoSCpDefendStatisticsEntry OBJECT-TYPE
        SYNTAX HwXQoSCpDefendStatisticsEntry
        MAX-ACCESS not-accessible
        STATUS current
        DESCRIPTION
            "A table of statistics information on attack defense"
        INDEX { hwXQoSCpDefendChassisID, hwXQoSCpDefendSlotId, hwXQoSCpDefendObjectIndex }
        ::= { hwXQoSCpDefendStatisticsTable 1 }

    HwXQoSCpDefendStatisticsEntry ::=
        SEQUENCE {
            hwXQoSCpDefendSlotId
                Integer32,
            hwXQoSCpDefendObjectIndex
                Integer32,
            hwXQoSCpDefendPassedPackets
                Counter64,
            hwXQoSCpDefendPassedBytes
                Counter64,
            hwXQoSCpDefendPassedPacketRate
                Counter64,
            hwXQoSCpDefendPassedByteRate
                Counter64,
            hwXQoSCpDefendDiscardedPackets
                Counter64,
            hwXQoSCpDefendDiscardedBytes
                Counter64,
            hwXQoSCpDefendDiscardedPacketRate
                Counter64,
            hwXQoSCpDefendDiscardedByteRate
                Counter64,
            hwXQoSCpDefendDiscardedThreshold
                Counter32,
            hwXQoSCpDefendChassisID
                Integer32,
            hwXQoSCpDefendProtocolDescirption
                OCTET STRING,
            hwXQoSCpDefendIntfPassedNum
                OCTET STRING
            }

    hwXQoSCpDefendSlotId OBJECT-TYPE
        SYNTAX Integer32 (1..128)
        MAX-ACCESS read-only
        STATUS current
        DESCRIPTION
            "Slot number of statistics for attack defense."
        ::= { hwXQoSCpDefendStatisticsEntry 1 }

    hwXQoSCpDefendObjectIndex OBJECT-TYPE
        SYNTAX Integer32 (0..511)
        MAX-ACCESS read-only
        STATUS current
        DESCRIPTION
            "Index of attack defense object."
        ::= { hwXQoSCpDefendStatisticsEntry 2 }

    hwXQoSCpDefendPassedPackets OBJECT-TYPE
        SYNTAX Counter64
        MAX-ACCESS read-only
        STATUS current
        DESCRIPTION
            "Number of packets passed the attack defense."
        ::= { hwXQoSCpDefendStatisticsEntry 11 }

    hwXQoSCpDefendPassedBytes OBJECT-TYPE
        SYNTAX Counter64
        MAX-ACCESS read-only
        STATUS current
        DESCRIPTION
            "Number of bytes passed the attack defense."
        ::= { hwXQoSCpDefendStatisticsEntry 12 }

    hwXQoSCpDefendPassedPacketRate OBJECT-TYPE
        SYNTAX Counter64
        MAX-ACCESS read-only
        STATUS current
        DESCRIPTION
            "Rate of packets passed the attack defense. Unit: pps"
        ::= { hwXQoSCpDefendStatisticsEntry 13 }

    hwXQoSCpDefendPassedByteRate OBJECT-TYPE
        SYNTAX Counter64
        MAX-ACCESS read-only
        STATUS current
        DESCRIPTION
            "Rate of bytes passed the attack defense. Unit: Byte/s"
        ::= { hwXQoSCpDefendStatisticsEntry 14 }

    hwXQoSCpDefendDiscardedPackets OBJECT-TYPE
        SYNTAX Counter64
        MAX-ACCESS read-only
        STATUS current
        DESCRIPTION
            "Number of packets discarded in the attack defense."
        ::= { hwXQoSCpDefendStatisticsEntry 15 }

    hwXQoSCpDefendDiscardedBytes OBJECT-TYPE
        SYNTAX Counter64
        MAX-ACCESS read-only
        STATUS current
        DESCRIPTION
            "Number of bytes discarded in the attack defense."
        ::= { hwXQoSCpDefendStatisticsEntry 16 }

    hwXQoSCpDefendDiscardedPacketRate OBJECT-TYPE
        SYNTAX Counter64
        MAX-ACCESS read-only
        STATUS current
        DESCRIPTION
            "Rate of packets discarded in the attack defense. Unit: pps"
        ::= { hwXQoSCpDefendStatisticsEntry 17 }

    hwXQoSCpDefendDiscardedByteRate OBJECT-TYPE
        SYNTAX Counter64
        MAX-ACCESS read-only
        STATUS current
        DESCRIPTION
            "Rate of bytes discarded in the attack defense. Unit: Byte/s"
        ::= { hwXQoSCpDefendStatisticsEntry 18 }

    hwXQoSCpDefendDiscardedThreshold OBJECT-TYPE
        SYNTAX Counter32
        MAX-ACCESS read-only
        STATUS current
        DESCRIPTION
            "Discarded packets threshold of alarm. Unit: packets"
        ::= { hwXQoSCpDefendStatisticsEntry 19 }

    hwXQoSCpDefendChassisID OBJECT-TYPE
        SYNTAX Integer32 (1..32)
        MAX-ACCESS read-only
        STATUS current
        DESCRIPTION
            "Chassis number of statistics for attack defense."
        ::= { hwXQoSCpDefendStatisticsEntry 20 }

    hwXQoSCpDefendProtocolDescirption OBJECT-TYPE
        SYNTAX OCTET STRING
        MAX-ACCESS read-only
        STATUS current
        DESCRIPTION
            "The descirption of Protocol."
        ::= { hwXQoSCpDefendStatisticsEntry 21 }

    hwXQoSCpDefendIntfPassedNum OBJECT-TYPE
        SYNTAX OCTET STRING
        MAX-ACCESS read-only
        STATUS current
        DESCRIPTION
            "Number of packets to be sent to the CPU on an interface."
        ::= { hwXQoSCpDefendStatisticsEntry 22 }

-- Urpf discard statistics
    hwXQoSUrpfObjects OBJECT IDENTIFIER ::= { hwXQoSObjects 7 }

    hwXQoSUrpfDiscardStatisticsTable OBJECT-TYPE
        SYNTAX SEQUENCE OF HwXQoSUrpfDiscardStatisticsEntry
        MAX-ACCESS not-accessible
        STATUS current
        DESCRIPTION
            "A table of statistics on discarded packets for IP URPF"
        ::= { hwXQoSUrpfObjects 1 }

    hwXQoSUrpfDiscardStatisticsEntry OBJECT-TYPE
        SYNTAX HwXQoSUrpfDiscardStatisticsEntry
        MAX-ACCESS not-accessible
        STATUS current
        DESCRIPTION
            "Urpf discard statistics entry"
        INDEX { hwXQoSUrpfSlotPhysicalIndex }
        ::= { hwXQoSUrpfDiscardStatisticsTable 1 }

    HwXQoSUrpfDiscardStatisticsEntry ::=
        SEQUENCE {
            hwXQoSUrpfSlotPhysicalIndex
                Integer32,
            hwXQoSUrpfDiscardedPackets
                Counter64
                }

    hwXQoSUrpfSlotPhysicalIndex OBJECT-TYPE
        SYNTAX Integer32
        MAX-ACCESS not-accessible
        STATUS current
        DESCRIPTION
            "The index of hwXQoSUrpfDiscardStatisticsTable.This index is identical to entPhysicalIndex in ENTITY-MIB."
        ::= { hwXQoSUrpfDiscardStatisticsEntry 1 }

    hwXQoSUrpfDiscardedPackets OBJECT-TYPE
        SYNTAX Counter64
        MAX-ACCESS read-only
        STATUS current
        DESCRIPTION
            "Number of packets discarded."
        ::= { hwXQoSUrpfDiscardStatisticsEntry 2 }

    hwXQoSVlanCfgObjects OBJECT IDENTIFIER ::= { hwXQoSObjects 8 }

    hwXQoSVlanCfgTable OBJECT-TYPE
        SYNTAX SEQUENCE OF HwXQoSVlanCfgEntry
        MAX-ACCESS not-accessible
        STATUS current
        DESCRIPTION
            "The table of vlan config information."
        ::= { hwXQoSVlanCfgObjects 1 }

    hwXQoSVlanCfgEntry OBJECT-TYPE
        SYNTAX HwXQoSVlanCfgEntry
        MAX-ACCESS not-accessible
        STATUS current
        DESCRIPTION
            "Vlan config information entry."
        INDEX { hwXQosVlanStatVlanId }
        ::= { hwXQoSVlanCfgTable 1 }

    HwXQoSVlanCfgEntry ::=
        SEQUENCE {
            hwXQoSVlanStatEnable
                EnabledStatus
            }

    hwXQoSVlanStatEnable OBJECT-TYPE
        SYNTAX EnabledStatus
        MAX-ACCESS read-write
        STATUS current
        DESCRIPTION
            "Vlan statistics enable: enable(1),disable(2)."
        ::= { hwXQoSVlanCfgEntry 1 }

-- Redirect multi-ip
    hwXQoSRedirectNextHopObjects OBJECT IDENTIFIER ::= { hwXQoSObjects 9 }

    hwXQoSRedirectNextHopTable OBJECT-TYPE
        SYNTAX SEQUENCE OF HwXQoSRedirectNextHopEntry
        MAX-ACCESS not-accessible
        STATUS current
        DESCRIPTION
            "A table of the redirect next hop"
        ::= { hwXQoSRedirectNextHopObjects 1 }

    hwXQoSRedirectNextHopEntry OBJECT-TYPE
        SYNTAX HwXQoSRedirectNextHopEntry
        MAX-ACCESS not-accessible
        STATUS current
        DESCRIPTION
            "A table of the redirect next hop information"
        INDEX { hwXQoSRedirectNextHopBehaviorName }
        ::= { hwXQoSRedirectNextHopTable 1 }

    HwXQoSRedirectNextHopEntry ::=
        SEQUENCE {
            hwXQoSRedirectNextHopBehaviorName
                OCTET STRING,
            hwXQoSRedirectNextHopOldIp
                IpAddress,
            hwXQoSRedirectNextHopNewIp
                IpAddress
            }

    hwXQoSRedirectNextHopBehaviorName OBJECT-TYPE
        SYNTAX OCTET STRING (SIZE (1..127))
        MAX-ACCESS read-only
        STATUS current
        DESCRIPTION
            "Traffic behavior name."
        ::= { hwXQoSRedirectNextHopEntry 1 }

    hwXQoSRedirectNextHopOldIp OBJECT-TYPE
        SYNTAX IpAddress
        MAX-ACCESS read-only
        STATUS current
        DESCRIPTION
            "The redirect next hop."
        ::= { hwXQoSRedirectNextHopEntry 2 }

    hwXQoSRedirectNextHopNewIp OBJECT-TYPE
        SYNTAX IpAddress
        MAX-ACCESS read-only
        STATUS current
        DESCRIPTION
            "The redirect next hop."
        ::= { hwXQoSRedirectNextHopEntry 3 }

-- irsm

    hwXQoSIrsmObjects OBJECT IDENTIFIER ::= { hwXQoSObjects 10 }

        hwXQoSIrsmTable OBJECT-TYPE
        SYNTAX SEQUENCE OF HwXQoSIrsmEntry
        MAX-ACCESS not-accessible
        STATUS current
        DESCRIPTION
            "A table of Irsm "
        ::= { hwXQoSIrsmObjects 1 }

    hwXQoSIrsmEntry OBJECT-TYPE
        SYNTAX HwXQoSIrsmEntry
        MAX-ACCESS not-accessible
        STATUS current
        DESCRIPTION
            "A table of Irsm"
        INDEX { hwXQoSIrsmSourceAddress}
        ::= { hwXQoSIrsmTable 1 }

    HwXQoSIrsmEntry ::=
        SEQUENCE {
            hwXQoSIrsmSourceAddress
                IpAddress,
            hwXQoSIrsmGroupAddress
                IpAddress,
            hwXQoSIrsmTime
                TimeTicks,
            hwXQoSIrsmDelay
                Integer32,
            hwXQoSIrsmThreshold
                Integer32,
            hwXQoSIrsmUpstream
                IpAddress,
            hwXQoSIrsmLocal
                IpAddress,
            hwXQoSIrsmTotalPacket
                Integer32,
            hwXQoSIrsmDropPacket
                Integer32
        }

    hwXQoSIrsmSourceAddress OBJECT-TYPE
        SYNTAX IpAddress
        MAX-ACCESS read-only
        STATUS current
        DESCRIPTION
            "hwXQoSIrsmSourceAddress "
        ::= { hwXQoSIrsmEntry 1 }

    hwXQoSIrsmGroupAddress OBJECT-TYPE
        SYNTAX IpAddress
        MAX-ACCESS read-only
        STATUS current
        DESCRIPTION
            "hwXQoSIrsmGroupAddress "
        ::= { hwXQoSIrsmEntry 2 }

    hwXQoSIrsmTime OBJECT-TYPE
        SYNTAX TimeTicks
        MAX-ACCESS read-only
        STATUS current
        DESCRIPTION
            "hwXQoSIrsmTime "
        ::= { hwXQoSIrsmEntry 3 }

    hwXQoSIrsmDelay OBJECT-TYPE
        SYNTAX Integer32
        MAX-ACCESS read-only
        STATUS current
        DESCRIPTION
            "hwXQoSIrsmDelay "
        ::= { hwXQoSIrsmEntry 4 }

    hwXQoSIrsmThreshold OBJECT-TYPE
        SYNTAX Integer32
        MAX-ACCESS read-only
        STATUS current
        DESCRIPTION
            "hwXQoSIrsmThreshold "
        ::= { hwXQoSIrsmEntry 5 }

    hwXQoSIrsmUpstream OBJECT-TYPE
        SYNTAX IpAddress
        MAX-ACCESS read-only
        STATUS current
        DESCRIPTION
            "hwXQoSIrsmUpstream "
        ::= { hwXQoSIrsmEntry 6 }

    hwXQoSIrsmLocal OBJECT-TYPE
        SYNTAX IpAddress
        MAX-ACCESS read-only
        STATUS current
        DESCRIPTION
            "hwXQoSIrsmLocal "
        ::= { hwXQoSIrsmEntry 7 }

    hwXQoSIrsmTotalPacket OBJECT-TYPE
        SYNTAX Integer32
        MAX-ACCESS read-only
        STATUS current
        DESCRIPTION
            "hwXQoSIrsmTotalPacket "
        ::= { hwXQoSIrsmEntry 8 }

    hwXQoSIrsmDropPacket OBJECT-TYPE
        SYNTAX Integer32
        MAX-ACCESS read-only
        STATUS current
        DESCRIPTION
            "hwXQoSIrsmDropPacket "
        ::= { hwXQoSIrsmEntry 9 }

    -- alarm

    hwXQoSNotifications OBJECT IDENTIFIER ::= { hwXQoSObjects 11 }

    hwXQoSCpDefendDiscardedRateAlarm NOTIFICATION-TYPE
        OBJECTS { hwXQoSCpDefendDiscardedPacketRate }
        STATUS current
        DESCRIPTION
            "Rate alarm of packets in the attack defense."
            ::= { hwXQoSNotifications 1 }
    hwXQoSQueueDiscardThresholdTrap NOTIFICATION-TYPE
        OBJECTS  {
                hwXQoSFrameId ,
                hwXQoSSlotId ,
                hwXQoSPortId ,
                hwXQoSTrapIfName ,
                hwXQoSTrapQueueId ,
                hwXQoSTrapDiscardPackets
                }
        STATUS   current
        DESCRIPTION
            "The SNMP trap is generated when the number of packages
            that queue discard is larger than the configured threshold."
        ::= { hwXQoSNotifications 2 }

    hwXQoSCpDefendDiscardedPacketAlarm NOTIFICATION-TYPE
        OBJECTS {
            hwXQoSCpDefendSlotId,
            hwXQoSCpDefendObjectIndex,
            hwXQoSCpDefendDiscardedPackets,
            hwXQoSCpDefendDiscardedThreshold,
            hwXQoSCpDefendChassisID,
            hwXQoSCpDefendProtocolDescirption
            }
        STATUS current
        DESCRIPTION
        "This object indicates the number of discarded packets due to CPU attack defense alarm threshold crossing."
        ::= { hwXQoSNotifications 3 }

    hwXQoSCpDefendDiscardedPacketAlarmClear NOTIFICATION-TYPE
        OBJECTS {
            hwXQoSCpDefendSlotId,
            hwXQoSCpDefendObjectIndex,
            hwXQoSCpDefendDiscardedPackets,
            hwXQoSCpDefendDiscardedThreshold,
            hwXQoSCpDefendChassisID,
            hwXQoSCpDefendProtocolDescirption
            }
        STATUS current
        DESCRIPTION
        "This object indicates the number of discarded packets when the alarm is cleared."
        ::= { hwXQoSNotifications 4 }

    hwXQoSCprlDiscardedPacketAlarm NOTIFICATION-TYPE
        OBJECTS {
            hwXQoSCpRateLimitIfIndex,
            hwXQoSCpRateLimitPeVidValue,
            hwXQoSCpRateLimitCeVidBegin
            }
        STATUS current
        DESCRIPTION
        "Number of packets discarded in the attack defense alarm."
        ::= { hwXQoSNotifications 5 }

    hwXQoSCprlDiscardedPacketAlarmClear NOTIFICATION-TYPE
        OBJECTS {
            hwXQoSCpRateLimitIfIndex,
            hwXQoSCpRateLimitPeVidValue,
            hwXQoSCpRateLimitCeVidBegin
            }
        STATUS current
        DESCRIPTION
        "Number of packets discarded in the attack defense alarm clearing."
        ::= { hwXQoSNotifications 6 }

    hwXQoSRedirectNextHopChangedAlarm NOTIFICATION-TYPE
        OBJECTS  {
                hwXQoSRedirectNextHopBehaviorName ,
                hwXQoSRedirectNextHopOldIp ,
                hwXQoSRedirectNextHopNewIp
                }
        STATUS   current
        DESCRIPTION
            "The SNMP trap is the redirect next hop changed."
        ::= { hwXQoSNotifications 7 }

    hwXQoSIrsmDelayAlarm NOTIFICATION-TYPE
        OBJECTS {
            hwXQoSIrsmSourceAddress,
            hwXQoSIrsmGroupAddress,
            hwXQoSIrsmTime,
            hwXQoSIrsmDelay,
            hwXQoSIrsmThreshold,
            hwXQoSIrsmUpstream,
            hwXQoSIrsmLocal
        }
        STATUS current
        DESCRIPTION
            "IRSM delay over threshold."
        ::= { hwXQoSNotifications 8 }

    hwXQoSIrsmDropPacketAlarm NOTIFICATION-TYPE
        OBJECTS {
            hwXQoSIrsmSourceAddress,
            hwXQoSIrsmGroupAddress,
            hwXQoSIrsmTime,
            hwXQoSIrsmTotalPacket,
            hwXQoSIrsmDropPacket,
            hwXQoSIrsmUpstream,
            hwXQoSIrsmLocal
        }
        STATUS current
        DESCRIPTION
            "IRSM multicast drop packets."
        ::= { hwXQoSNotifications 9 }

    hwXQoSIrsmSynFrameDropAlarm NOTIFICATION-TYPE
        OBJECTS {
            hwXQoSIrsmSourceAddress,
            hwXQoSIrsmGroupAddress,
            hwXQoSIrsmTime
        }
        STATUS current
        DESCRIPTION
            "IRSM syn frame drop."
        ::= { hwXQoSNotifications 10 }

    hwXQoSRuleFailAlarm NOTIFICATION-TYPE
        OBJECTS {
            hwXQoSRuleFailInfo
            }
        STATUS current
        DESCRIPTION
            "ACL Rule Exhaustion Alarm"
        ::= { hwXQoSNotifications 11 }

    hwXQoSProfileUsedAlarm NOTIFICATION-TYPE
        OBJECTS {
            hwXQoSProfileName
        }
        STATUS current
        DESCRIPTION
            "Qos-profile used."
        ::= { hwXQoSNotifications 12 }

    --port queue alarm
    hwXQoSPortQueueAlarm NOTIFICATION-TYPE
        OBJECTS {
            hwXQoSPortQueueAlarmIfIndex,
            hwXQoSPortQueueAlarmQueue,
            hwXQoSPortQueueAlarmTrunkIndex
            }
        STATUS current
        DESCRIPTION
            "hwXQoSPortQueueAlarm."
        ::= { hwXQoSNotifications 13 }

    hwXQoSPortQueueAlarmClear NOTIFICATION-TYPE
        OBJECTS {
            hwXQoSPortQueueAlarmIfIndex,
            hwXQoSPortQueueAlarmQueue,
            hwXQoSPortQueueAlarmTrunkIndex
            }
        STATUS current
        DESCRIPTION
            "hwXQoSPortQueueAlarmClear."
        ::= { hwXQoSNotifications 14 }
    --port queue alarm

    hwXQoSSecurityStormControlInterfaceTrap NOTIFICATION-TYPE
        OBJECTS {
            hwXQoSSecurityStormControlInterfaceChassisId,
            hwXQoSSecurityStormControlInterfaceSlotId,
            hwXQoSSecurityStormControlInterfaceName,
            hwXQoSSecurityStormControlInterfaceVlan}
        STATUS current
        DESCRIPTION
        "The SNMP trap is generated when the status of interface is changed for storm-control."
        ::= { hwXQoSNotifications 15 }

    hwXQoSResouceNotEnoughAlarmObjects OBJECT IDENTIFIER ::= { hwXQoSObjects 22 }

    hwXQoSStatResouceNotEnoughAlarm NOTIFICATION-TYPE
        OBJECTS {
            hwXQoSStatResouceNotEnoughSlotId,
            hwXQoSStatResouceNotEnoughStatType}
        STATUS current
        DESCRIPTION
            "The SNMP trap is generated when the specific statistics resource is not enough."
        ::= { hwXQoSNotifications 16 }
    hwXQoSCARResouceNotEnoughAlarm NOTIFICATION-TYPE
        OBJECTS {
            hwXQoSCARResouceNotEnoughSlotId,
            hwXQoSCARResouceNotEnoughCARType}
        STATUS current
        DESCRIPTION
            "The SNMP trap is generated when the specific car resource is not enough."
        ::= { hwXQoSNotifications 17 }

    hwXQoSRuleFailAlarmCancel NOTIFICATION-TYPE
        OBJECTS {
            hwXQoSRuleFailInfo
            }
        STATUS current
        DESCRIPTION
            "Clearance of ACL Rule Exhaustion Alarm"
        ::= { hwXQoSNotifications 18 }

--begin add by jinxiaoyan
    hwXQoSHardPipeAlarm NOTIFICATION-TYPE
        OBJECTS {
            hwXQoSHardPipeAlarmIfIndex,
            hwXQoSHardPipeAlarmUsage}
        STATUS current
        DESCRIPTION
            "When the hard-pipe bandwidth usage reached 95%, a warning alarm was generated. When the hard-pipe bandwidth usage reached 98%, a threshold-crossing alarm was generated."
        ::= { hwXQoSNotifications 19 }

    hwXQoSHardPipeAlarmClear NOTIFICATION-TYPE
        OBJECTS { hwXQoSHardPipeAlarmIfIndex }
        STATUS current
        DESCRIPTION
            "The hard-pipe service alarm on interface [InterfaceName] has cleared."
        ::= { hwXQoSNotifications 20 }

--end add by jinxiaoyan

    hwXQOSQueueBufferOverrunAlarm NOTIFICATION-TYPE
        OBJECTS {
            hwXQOSQueueBufferAlarmChassisID,
            hwXQOSQueueBufferAlarmSlotID,
            hwXQOSQueueBufferAlarmIfIndex,
            hwXQOSQueueBufferAlarmQueueID,
            hwXQOSQueueBufferAlarmUsedCell,
            hwXQOSQueueBufferAlarmUsedLength,
            hwXQOSQueueBufferAlarmThreshold,
            hwXQOSQueueBufferAlarmDiscard}
        STATUS current
        DESCRIPTION
            "The used buffer of queue is over the configured threshold."
        ::= { hwXQoSNotifications 21 }

    hwXQOSQueueBufferOverrunResume NOTIFICATION-TYPE
        OBJECTS {
            hwXQOSQueueBufferAlarmChassisID,
            hwXQOSQueueBufferAlarmSlotID,
            hwXQOSQueueBufferAlarmIfIndex,
            hwXQOSQueueBufferAlarmQueueID}
        STATUS current
        DESCRIPTION
            "The used buffer of queue is recovered from overrun."
        ::= { hwXQoSNotifications 22 }

    hwXQoSHardPipeCfgAlarm NOTIFICATION-TYPE
        OBJECTS {
            hwXQoSHardPipeCfgAlarmIfIndex}
        STATUS current
        DESCRIPTION
            "hwXQoSHardPipeCfgAlarm."
        ::= { hwXQoSNotifications 23 }

    hwXQoSHardPipeCfgAlarmClear NOTIFICATION-TYPE
        OBJECTS { hwXQoSHardPipeCfgAlarmIfIndex }
        STATUS current
        DESCRIPTION
            "hwXQoSHardPipeCfgAlarmClear."
        ::= { hwXQoSNotifications 24 }

    --hard-pipe alarm
    -- 1.3.6.1.4.1.2011.5.25.32.4.1.23.2
    hwXQoSHardPipeCfgAlarmTable OBJECT-TYPE
        SYNTAX SEQUENCE OF HwXQoSHardPipeCfgAlarmEntry
        MAX-ACCESS not-accessible
        STATUS current
        DESCRIPTION
            "hwXQoSHardPipeCfgAlarmTable"
        ::= { hwXQoSHardPipeAlarmObjects 2 }

    -- 1.3.6.1.4.1.2011.5.25.32.4.1.23.2.1
    hwXQoSHardPipeCfgAlarmEntry OBJECT-TYPE
        SYNTAX HwXQoSHardPipeCfgAlarmEntry
        MAX-ACCESS not-accessible
        STATUS current
        DESCRIPTION
            "hwXQoSHardPipeCfgAlarmEntry"
        INDEX { hwXQoSHardPipeCfgAlarmIfIndex }
        ::= { hwXQoSHardPipeCfgAlarmTable 1 }

    HwXQoSHardPipeCfgAlarmEntry ::=
        SEQUENCE {
            hwXQoSHardPipeCfgAlarmIfIndex
            OCTET STRING
            }

    -- 1.3.6.1.4.1.2011.5.25.32.4.1.23.2.1.1
    hwXQoSHardPipeCfgAlarmIfIndex OBJECT-TYPE
        SYNTAX OCTET STRING
        MAX-ACCESS read-only
        STATUS current
        DESCRIPTION
            "The interface index."
        ::= { hwXQoSHardPipeCfgAlarmEntry 1 }

-- end by sunhongliang

--1.3.6.1.4.1.2011.5.25.32.4.1.11.29
    hwXQoSVpnAclConflictAlarm NOTIFICATION-TYPE
        OBJECTS {
            hwXQoSVpnAclConflictAlarmVpnIndex,
            hwXQoSSlotNum}
    STATUS current
    DESCRIPTION
        "The traffic policy of a VPN instance did not take effect."
    ::= { hwXQoSNotifications 29 }

--1.3.6.1.4.1.2011.5.25.32.4.1.11.30
    hwXQoSVpnAclConflictAlarmClear NOTIFICATION-TYPE
        OBJECTS { hwXQoSVpnAclConflictAlarmVpnIndex,
            hwXQoSSlotNum}
    STATUS current
    DESCRIPTION
    "The alarm indicating the traffic policy ineffectiveness of a VPN instance was cleared, because the traffic policy took effect or was deleted."
    ::= { hwXQoSNotifications 30 }

    --begin add by liuxiaoyan
    --1.3.6.1.4.1.2011.5.25.32.4.1.11.31
    hwXQoSTrunkProfileNotEffectAlarm NOTIFICATION-TYPE
        OBJECTS {
            hwXQoSTrunkProfileNotEffectAlarmIfName,
            hwXQoSTrunkProfileNotEffectAlarmSlotid}
        STATUS current
         DESCRIPTION
            "hwXQoSTrunkProfileNotEffectAlarm."
        ::= { hwXQoSNotifications 31 }
    --end add by liuxiaoyan

        -- 1.3.6.1.4.1.2011.5.25.32.4.1.24
    hwXQoSVpnAclConflictAlarmObjects OBJECT IDENTIFIER ::= { hwXQoSObjects 24 }

    -- 1.3.6.1.4.1.2011.5.25.32.4.1.24.1
    hwXQoSVpnAclConflictAlarmTable OBJECT-TYPE
        SYNTAX SEQUENCE OF HwXQoSVpnAclConflictAlarmEntry
        MAX-ACCESS not-accessible
        STATUS current
        DESCRIPTION
            "hwXQoSVpnAclConflictAlarmTable"
        ::= { hwXQoSVpnAclConflictAlarmObjects 1 }

    -- 1.3.6.1.4.1.2011.5.25.32.4.1.24.1.1
    hwXQoSVpnAclConflictAlarmEntry OBJECT-TYPE
        SYNTAX HwXQoSVpnAclConflictAlarmEntry
        MAX-ACCESS not-accessible
        STATUS current
        DESCRIPTION
            "hwXQoSVpnAclConflictAlarmEntry"
        INDEX { hwXQoSVpnAclConflictAlarmVpnIndex, hwXQoSSlotNum }
        ::= { hwXQoSVpnAclConflictAlarmTable 1 }

    HwXQoSVpnAclConflictAlarmEntry ::=
        SEQUENCE {
            hwXQoSVpnAclConflictAlarmVpnIndex
                OCTET STRING,
            hwXQoSSlotNum
                Unsigned32
                }

    -- 1.3.6.1.4.1.2011.5.25.32.4.1.24.1.1.1
    hwXQoSVpnAclConflictAlarmVpnIndex OBJECT-TYPE
        SYNTAX OCTET STRING
        MAX-ACCESS read-only
        STATUS current
        DESCRIPTION
            "Vpn instance index."
        ::= { hwXQoSVpnAclConflictAlarmEntry 1 }

    -- 1.3.6.1.4.1.2011.5.25.32.4.1.24.1.1.2
    hwXQoSSlotNum  OBJECT-TYPE
        SYNTAX Unsigned32
        MAX-ACCESS read-only
        STATUS current
        DESCRIPTION "The slot number"
        ::= { hwXQoSVpnAclConflictAlarmEntry  2 }


    hwXQoSIfLrDiscardAlarm NOTIFICATION-TYPE
        OBJECTS {
            hwXQoSIfLrDiscardAlarmIfIndex,
            hwXQoSIfLrDiscardAlarmIfName,
            hwXQoSIfLrDiscardAlarmCir,
            hwXQoSIfLrDiscardAlarmTrapThreshold,
            hwXQoSIfLrDiscardAlarmPassPacketRate
            }
        STATUS current
        DESCRIPTION
            "The SNMP trap is when the outbound traffic bandwidth is over the threshold."
        ::= { hwXQoSNotifications 25 }

    hwXQoSIfLrDiscardAlarmResume NOTIFICATION-TYPE
        OBJECTS {
            hwXQoSIfLrDiscardAlarmIfIndex,
            hwXQoSIfLrDiscardAlarmIfName,
            hwXQoSIfLrDiscardAlarmCir,
            hwXQoSIfLrDiscardAlarmTrapThreshold
            }
        STATUS current
        DESCRIPTION
            "The SNMP trap is when the outbound traffic bandwidth is recovered from congestion."
        ::= { hwXQoSNotifications 26 }

    hwXQoSFCoEPriorityAlarm NOTIFICATION-TYPE
        STATUS current
        DESCRIPTION
            "The SNMP trap is when the FCoE packet priority may be incorrect."
        ::= { hwXQoSNotifications 27 }

    hwXQoSFCoEPriorityAlarmClear NOTIFICATION-TYPE
        STATUS current
        DESCRIPTION
            "The SNMP trap is when the FCoE packet priority alarm is clearing."
        ::= { hwXQoSNotifications 28 }

    hwXQoSQppbPolicyApplyFailAlarm NOTIFICATION-TYPE
        OBJECTS {
                hwXQoSQppbPolicyApplyFailChassisID,
                hwXQoSQppbPolicyApplyFailSlotId,
                hwXQoSQppbPolicyApplyFailInterfaceName,
                hwXQoSQppbPolicyApplyFailDirection,
                hwXQoSQppbPolicyApplyFailLocalID }
        STATUS current
        DESCRIPTION
            "The SNMP trap is generated when the qppb policy applied failed."
        ::= { hwXQoSNotifications 32 }

    hwXQoSQppbPolicyApplyFailAlarmClear NOTIFICATION-TYPE
        OBJECTS {
                hwXQoSQppbPolicyApplyFailChassisID,
                hwXQoSQppbPolicyApplyFailSlotId,
                hwXQoSQppbPolicyApplyFailInterfaceName,
                hwXQoSQppbPolicyApplyFailDirection,
                hwXQoSQppbPolicyApplyFailLocalID }
        STATUS current
        DESCRIPTION
            "Clear the SNMP trap is generated when the qppb policy applied failed."
        ::= { hwXQoSNotifications 33 }

    hwXQoSIfQPPBDelAlarm NOTIFICATION-TYPE
        OBJECTS {
                hwXQoSIfQPPBDelInterfaceName,
                hwXQoSIfQPPBDelPolicyName,
                hwXQoSIfQPPBDelDirection,
                hwXQoSIfQPPBDelDiscrip}
        STATUS current
        DESCRIPTION
            "The SNMP trap is generated when the interface qppb policy deleted because of conflict."
        ::= { hwXQoSNotifications 34 }

    hwXQoSDefendPortCarPassedPacketAlarm NOTIFICATION-TYPE
        OBJECTS {
            hwXQoSCpDefendChassisID,
            hwXQoSCpDefendSlotId,
            hwXQoSCpDefendObjectIndex,
            hwXQoSCpDefendIntfPassedNum,
            hwXQoSCpDefendPassedPackets,
            hwXQoSCpDefendDiscardedThreshold}
        STATUS current
        DESCRIPTION
            "The number of packets sent to the CPU by port car exceeded the threshold on an interface."
        ::= { hwXQoSNotifications 35 }

    hwXQoSDefendPortCarPassedPacketAlarmClear NOTIFICATION-TYPE
        OBJECTS {
            hwXQoSCpDefendChassisID,
            hwXQoSCpDefendSlotId,
            hwXQoSCpDefendObjectIndex,
            hwXQoSCpDefendIntfPassedNum,
            hwXQoSCpDefendPassedPackets,
            hwXQoSCpDefendDiscardedThreshold}
        STATUS current
        DESCRIPTION
            "The number of packets sent to the CPU by port car fell below the threshold on an interface."
        ::= { hwXQoSNotifications 36 }

    hwXQoSGlbQPPBEventLog NOTIFICATION-TYPE
        OBJECTS {
                hwXQoSGlbQPPBEventSlotId,
                hwXQoSGlbQPPBEventFunction,
                hwXQoSGlbQPPBEventDiscrip }
        STATUS current
        DESCRIPTION
            "The SNMP trap is generated when The global QPPB will not be effective."
        ::= { hwXQoSNotifications 37 }

    hwXQoSQppbPolicyEventLog NOTIFICATION-TYPE
        OBJECTS {
        hwXQoSQppbPolicyChassisID,
        hwXQoSQppbPolicySlotId }
        STATUS current
        DESCRIPTION
            "The SNMP trap is generated when The QPPB Policy will not be effective."
        ::= { hwXQoSNotifications 38 }

--begin add by xuechenguang
    hwXQoSSoftPipeAlarm NOTIFICATION-TYPE
            OBJECTS {
            hwXQoSSoftPipeAlarmIfIndex,
            hwXQoSSoftPipeAlarmUsage}
     STATUS current
     DESCRIPTION
    "The softpipe bandwidth usage reached the threshold alarm."
    ::= { hwXQoSNotifications 39 }

    hwXQoSSoftPipeAlarmClear NOTIFICATION-TYPE
            OBJECTS { hwXQoSSoftPipeAlarmIfIndex }
     STATUS current
     DESCRIPTION
    "The soft pipe bandwidth usage below the threshold alarm."
    ::= { hwXQoSNotifications 40 }
-- end by xuechenguang

    hwXQoSMulticastPktsDiscardAlarm NOTIFICATION-TYPE
        OBJECTS {
            hwXQoSMulticastPktsDiscardAlarmSlotid
            }
        STATUS current
        DESCRIPTION
            "The SNMP trap is generated when the multicast packets are discarded."
        ::= { hwXQoSNotifications 41}

    hwXQoSMulticastPktsDiscardAlarmResume NOTIFICATION-TYPE
        OBJECTS {
            hwXQoSMulticastPktsDiscardAlarmSlotid
            }
        STATUS current
        DESCRIPTION
            "Clear the SNMP trap which is generated when the multicast packets are discarded."
        ::= { hwXQoSNotifications 42}

    hwXQoSMulticastPktsDiscardInterfaceAlarm NOTIFICATION-TYPE
        OBJECTS {
            hwXQoSMulticastPktsDiscardInterfaceAlarmIfIndex,
            hwXQoSMulticastPktsDiscardInterfaceAlarmIfName
            }
        STATUS current
        DESCRIPTION
            "The SNMP trap is generated when the multicast packets are discarded."
        ::= { hwXQoSNotifications 43 }

    hwXQoSMulticastPktsDiscardInterfaceAlarmResume NOTIFICATION-TYPE
        OBJECTS {
            hwXQoSMulticastPktsDiscardInterfaceAlarmIfIndex,
            hwXQoSMulticastPktsDiscardInterfaceAlarmIfName
            }
        STATUS current
        DESCRIPTION
            "Clear the SNMP trap which is generated when the multicast packets are discarded."
        ::= { hwXQoSNotifications 44 }

    hwXQoSUnicastPktsDiscardAlarm NOTIFICATION-TYPE
        OBJECTS {
            hwXQoSUnicastPktsDiscardAlarmSlotid
            }
        STATUS current
        DESCRIPTION
            "The SNMP trap is generated when the unicast packets are discarded."
        ::= { hwXQoSNotifications 55}

    hwXQoSUnicastPktsDiscardAlarmResume NOTIFICATION-TYPE
        OBJECTS {
            hwXQoSUnicastPktsDiscardAlarmSlotid
            }
        STATUS current
        DESCRIPTION
            "Clear the SNMP trap which is generated when the unicast packets are discarded."
        ::= { hwXQoSNotifications 56}

    hwXQoSUnicastPktsCongestionInterfaceAlarm NOTIFICATION-TYPE
        OBJECTS {
            hwXQoSUnicastPktsCongestionInterfaceAlarmIfName,
            hwXQoSUnicastPktsCongestionInterfaceAlarmDirection
            }
        STATUS current
        DESCRIPTION
            "The SNMP trap is generated when the Unicast packets are congested."
        ::= { hwXQoSNotifications 49 }

    hwXQoSUnicastPktsCongestionInterfaceAlarmResume NOTIFICATION-TYPE
        OBJECTS {
            hwXQoSUnicastPktsCongestionInterfaceAlarmIfName,
            hwXQoSUnicastPktsCongestionInterfaceAlarmDirection
            }
        STATUS current
        DESCRIPTION
            "Clear the SNMP trap which is generated when the Unicast packets are congested."
        ::= { hwXQoSNotifications 50 }

    hwXQoSPacketsDropInterfaceAlarm NOTIFICATION-TYPE
        OBJECTS {
            hwXQoSPacketsDropInterfaceAlarmIfName,
            hwXQoSPacketsDropInterfaceAlarmQueueId,
            hwXQoSPacketsDropInterfaceAlarmSlotId,
            hwXQoSPacketsDropInterfaceAlarmPackets,
            hwXQoSPacketsDropInterfaceAlarmBytes
            }
        STATUS current
        DESCRIPTION
            "The SNMP trap is generated when packets are dropped."
        ::= { hwXQoSNotifications 51 }

    hwXQoSPacketsDropInterfaceAlarmResume NOTIFICATION-TYPE
        OBJECTS {
            hwXQoSPacketsDropInterfaceAlarmIfName,
            hwXQoSPacketsDropInterfaceAlarmQueueId,
            hwXQoSPacketsDropInterfaceAlarmSlotId,
            hwXQoSPacketsDropInterfaceAlarmPackets,
            hwXQoSPacketsDropInterfaceAlarmBytes
            }
        STATUS current
        DESCRIPTION
            "Clear the SNMP trap which is generated when no more packets are dropped."
        ::= { hwXQoSNotifications 52 }

    hwXQoSRcyPortPktsDropAlarm NOTIFICATION-TYPE
        OBJECTS {
            hwXQoSRcyPortPktsDropAlarmPortId,
            hwXQoSRcyPortPktsDropAlarmSlotId,
            hwXQoSRcyPortPktsDropAlarmChipId
            }
        STATUS current
        DESCRIPTION
            "The SNMP trap is generated when packets are dropped."
        ::= { hwXQoSNotifications 53 }

    hwXQoSRcyPortPktsDropAlarmResume NOTIFICATION-TYPE
        OBJECTS {
            hwXQoSRcyPortPktsDropAlarmPortId,
            hwXQoSRcyPortPktsDropAlarmSlotId,
            hwXQoSRcyPortPktsDropAlarmChipId
            }
        STATUS current
        DESCRIPTION
            "Clear the SNMP trap which is generated when no more packets are dropped."
        ::= { hwXQoSNotifications 54 }

--begin add by sunqirui
    hwXQoSStormSuppressAlarm NOTIFICATION-TYPE
        OBJECTS { hwXQoSStormSuppressAlarmIfIndex, hwXQoSStormSuppressAlarmIfName }
        STATUS current
        DESCRIPTION
            "The SNMP trap is generated when the port has packets dropped caused by storm suppression.
            hwXQoSStormSuppressAlarmIfIndex: The interface index, equal to ifIndex.
            hwXQoSStormSuppressAlarmIfName: The interface name."
        ::= { hwXQoSNotifications 57 }


    hwXQoSStormSuppressAlarmResume NOTIFICATION-TYPE
        OBJECTS { hwXQoSStormSuppressAlarmIfIndex, hwXQoSStormSuppressAlarmIfName }
        STATUS current
        DESCRIPTION
            "The SNMP trap is generated when the port has recovered from packets dropped caused by storm suppression.
            hwXQoSStormSuppressAlarmIfIndex: The interface index, equal to ifIndex.
            hwXQoSStormSuppressAlarmIfName: The interface name."
        ::= { hwXQoSNotifications 58 }
        hwXQoSStormSuppressSlotAlarm NOTIFICATION-TYPE
        OBJECTS { hwXQoSStormSuppressSlotAlarmSlot }
        STATUS current
        DESCRIPTION
            "The SNMP trap is generated when the port has dropped packets because of storm suppress."
        ::= { hwXQoSNotifications 59 }

    hwXQoSStormSuppressSlotAlarmResume NOTIFICATION-TYPE
        OBJECTS { hwXQoSStormSuppressSlotAlarmSlot }
        STATUS current
        DESCRIPTION
            "The SNMP trap is generated when the port is recovered from dropped packets because of storm suppress."
        ::= { hwXQoSNotifications 60 }
--end add by sunqirui

    hwXQoSIngressPktsDiscardAlarm NOTIFICATION-TYPE
        OBJECTS {
            hwXQoSIngressPktsDiscardAlarmSlotid
            }
        STATUS current
        DESCRIPTION
            "The SNMP trap is generated when the ingress packets are discarded."
        ::= { hwXQoSNotifications 63}

    hwXQoSIngressPktsDiscardAlarmResume NOTIFICATION-TYPE
        OBJECTS {
            hwXQoSIngressPktsDiscardAlarmSlotid
            }
        STATUS current
        DESCRIPTION
            "Clear the SNMP trap which is generated when the ingress packets are discarded."
        ::= { hwXQoSNotifications 64}

    hwXQoSIfCarDiscardAlarm NOTIFICATION-TYPE
        OBJECTS {
            hwXQoSIfCarDiscardAlarmSlotid,
            hwXQoSIfCarDiscardAlarmIfName,
            hwXQoSIfCarDiscardAlarmDirection
            }
        STATUS current
        DESCRIPTION
            "The SNMP trap is generated when the IfCar are discarded."
        ::= { hwXQoSNotifications 69}

    hwXQoSIfCarDiscardAlarmResume NOTIFICATION-TYPE
        OBJECTS {
            hwXQoSIfCarDiscardAlarmSlotid,
            hwXQoSIfCarDiscardAlarmIfName,
            hwXQoSIfCarDiscardAlarmDirection
            }
        STATUS current
        DESCRIPTION
            "Clear the SNMP trap which is generated when the IfCar are discarded."
        ::= { hwXQoSNotifications 70}

    hwXQosQueueExcepAlarm NOTIFICATION-TYPE
        OBJECTS {
            hwXQosQueueExcepAlarmSlotId,
            hwXQosQueueExcepAlarmProtocal
            }
        STATUS current
        DESCRIPTION
            "The SNMP trap is generated when queue exception leads to non forwarding."
        ::= { hwXQoSNotifications 71}

    hwXQosQueueExcepAlarmResume NOTIFICATION-TYPE
        OBJECTS {
            hwXQosQueueExcepAlarmSlotId,
            hwXQosQueueExcepAlarmProtocal
            }
        STATUS current
        DESCRIPTION
            "Clear the SNMP trap which is generated when queue exception leads to non forwarding."
        ::= { hwXQoSNotifications 72}

    hwXQoSPfcTurnOffAlarm NOTIFICATION-TYPE
        OBJECTS {
            hwXQoSPfcTurnOffAlarmIfName,
            hwXQoSPfcTurnOffAlarmPriority,
            hwXQoSPfcTurnOffAlarmDetectedNumber,
            hwXQoSPfcTurnOffAlarmThreshold
            }
        STATUS current
        DESCRIPTION
            "The SNMP trap is generated when pfc thresholds exceeded priority turn off threshold."
        ::= { hwXQoSNotifications 73}

    hwXQoSPfcTurnOffResume NOTIFICATION-TYPE
        OBJECTS {
            hwXQoSPfcTurnOffAlarmIfName,
            hwXQoSPfcTurnOffAlarmPriority
            }
        STATUS current
        DESCRIPTION
            "Clear the SNMP trap which is generated when undo priority turn off threshold config."
        ::= { hwXQoSNotifications 74}

    hwXQoSModuleAlarmPatchStub NOTIFICATION-TYPE
        OBJECTS {
            hwXQoSModuleAlarmPatchStubModule
            }
        STATUS current
        DESCRIPTION
            "The SNMP trap is generated when the module is unstable."
        ::= { hwXQoSNotifications 138}

    hwXQoSModuleAlarmPatchStubResume NOTIFICATION-TYPE
        OBJECTS {
            hwXQoSModuleAlarmPatchStubResumeModule
            }
        STATUS current
        DESCRIPTION
            "Clear the SNMP trap which is generated when the module status is restored."
        ::= { hwXQoSNotifications 139}

    hwXQoSSlotAlarmPatchStub NOTIFICATION-TYPE
        OBJECTS {
            hwXQoSSlotAlarmPatchStubModule
            }
        STATUS current
        DESCRIPTION
            "The SNMP trap is generated when the slot is unstable."
        ::= { hwXQoSNotifications 140}

    hwXQoSSlotAlarmPatchStubResume NOTIFICATION-TYPE
        OBJECTS {
            hwXQoSSlotAlarmPatchStubResumeModule
            }
        STATUS current
        DESCRIPTION
            "Clear the SNMP trap which is generated when the slot status is restored."
        ::= { hwXQoSNotifications 141}

    hwXQoSDevAlarmPatchStub NOTIFICATION-TYPE
        OBJECTS {
            hwXQoSDevAlarmPatchStubModule
            }
        STATUS current
        DESCRIPTION
            "The SNMP trap is generated when the device is unstable."
        ::= { hwXQoSNotifications 142}

    hwXQoSDevAlarmPatchStubResume NOTIFICATION-TYPE
        OBJECTS {
            hwXQoSDevAlarmPatchStubResumeModule
            }
        STATUS current
        DESCRIPTION
            "Clear the SNMP trap which is generated when the device status is restored."
        ::= { hwXQoSNotifications 143}

    hwXQoSOutPfcTurnOffAlarm NOTIFICATION-TYPE
        OBJECTS {
            hwXQoSOutPfcTurnOffAlarmIfName,
            hwXQoSOutPfcTurnOffAlarmPriority,
            hwXQoSOutPfcTurnOffAlarmDetectedNumber,
            hwXQoSOutPfcTurnOffAlarmBuffUsage,
            hwXQoSOutPfcTurnOffAlarmThreshold
            }
        STATUS current
        DESCRIPTION
            "The SNMP trap is generated when out pfc thresholds exceeded priority turn off threshold."
        ::= { hwXQoSNotifications 126}

    hwXQoSOutPfcTurnOffResume NOTIFICATION-TYPE
        OBJECTS {
            hwXQoSPfcTurnOffAlarmIfName,
            hwXQoSPfcTurnOffAlarmPriority
            }
        STATUS current
        DESCRIPTION
            "Clear the SNMP trap which is generated when undo priority turn off threshold config."
        ::= { hwXQoSNotifications 127}

    hwXQoSPfcDeadLockAlarm NOTIFICATION-TYPE
        OBJECTS {
            hwXQoSPfcDeadLockAlarmIfName,
            hwXQoSPfcDeadLockAlarmPriority,
            hwXQoSPfcDeadLockAlarmDetectedNumber,
            hwXQoSPfcDeadLockAlarmRecoveredNumber
            }
        STATUS current
        DESCRIPTION
            "The SNMP trap is generated when detected number of times this time than the last count increased or less than."
        ::= { hwXQoSNotifications 75}

    hwXQoSPfcDeadLockResume NOTIFICATION-TYPE
        OBJECTS {
            hwXQoSPfcDeadLockAlarmIfName,
            hwXQoSPfcDeadLockAlarmPriority
            }
        STATUS current
        DESCRIPTION
            "Clear the SNMP trap which is generated when detected number this time is not increased than the last count."
        ::= { hwXQoSNotifications 76}

    hwXACLFEIMemoryFullAlarm NOTIFICATION-TYPE
        OBJECTS {
            hwXACLFEIMemoryFullAlarmSlotid
            }
        STATUS current
        DESCRIPTION
            "Memory resources are insufficient and the ACL service may not take effect."
        ::= { hwXQoSNotifications 77}

    hwXACLFEIMemoryFullAlarmResume NOTIFICATION-TYPE
        OBJECTS {
            hwXACLFEIMemoryFullAlarmSlotid
            }
        STATUS current
        DESCRIPTION
            "Delete useless configuration."
        ::= { hwXQoSNotifications 78}

    hwXQoSIngressAgingDiscardAlarm NOTIFICATION-TYPE
        OBJECTS {
            hwXQoSIngressAgingDiscardAlarmSlotid
            }
        STATUS current
        DESCRIPTION
            "The SNMP trap is generated when the ingress packets are deleted."
        ::= { hwXQoSNotifications 67}

    hwXQoSIngressAgingDiscardAlarmResume NOTIFICATION-TYPE
        OBJECTS {
            hwXQoSIngressAgingDiscardAlarmSlotid
            }
        STATUS current
        DESCRIPTION
            "Clear the SNMP trap which is generated when the ingress packets are deleted."
        ::= { hwXQoSNotifications 68}

    hwXQoSInterfaceIngressDropAlarm NOTIFICATION-TYPE
        OBJECTS {
            hwXQoSInterfaceIngressDropAlarmIfName
            }
        STATUS current
        DESCRIPTION
            "The SNMP trap is generated when the packages are discarded at port ingress."
        ::= { hwXQoSNotifications 81}

    hwXQoSInterfaceIngressDropAlarmResume NOTIFICATION-TYPE
        OBJECTS {
            hwXQoSInterfaceIngressDropAlarmIfName
            }
        STATUS current
        DESCRIPTION
            "Clear the SNMP trap which is generated when the packages are not discarded at port ingress."
        ::= { hwXQoSNotifications 82}

    hwXQoSHardPipeApplyFailAlarm NOTIFICATION-TYPE
        OBJECTS { hwXQoSHardPipeAlarmIfIndex }
        STATUS current
        DESCRIPTION
            "The IP hard pipe configured on an interface did not take effect."
        ::= { hwXQoSNotifications 45 }

    hwXQoSHardPipeApplyFailAlarmClear NOTIFICATION-TYPE
        OBJECTS { hwXQoSHardPipeAlarmIfIndex }
        STATUS current
        DESCRIPTION
            "This object indicates that the alarm indicating that the hard pipe on an interface does not take effect is cleared."
        ::= { hwXQoSNotifications 46 }

--begin add by lizhen
    hwXQoSHardPipeBwAlarm NOTIFICATION-TYPE
        OBJECTS {
        hwXQoSHardPipeBwAlarmIfIndex,
        hwXQoSHardPipeBwAlarmResvBw }
        STATUS current
        DESCRIPTION
            "The configed bandwidth value of hardpipe has exceeded the actual bandwidth value."
        ::= { hwXQoSNotifications 47 }

    hwXQoSHardPipeBwAlarmClear NOTIFICATION-TYPE
        OBJECTS { hwXQoSHardPipeBwAlarmIfIndex }
        STATUS current
        DESCRIPTION
            "The configed bandwidth value of hardpipe is equal to the actual bandwidth value."
        ::= { hwXQoSNotifications 48 }
--end by lizhen
--begin add by yangting
    hwXQoSHardPipeAcBandWthOverAlarm NOTIFICATION-TYPE
        OBJECTS { hwXQoSHardPipeAlarmIfIndex }
        STATUS current
        DESCRIPTION
            "The AC-side hard pipe bandwidth exceeded the interface bandwidth and became invalid."
        ::= { hwXQoSNotifications 61 }

    hwXQoSHardPipeAcBandWthOverAlarmClear NOTIFICATION-TYPE
        OBJECTS { hwXQoSHardPipeAlarmIfIndex }
        STATUS current
        DESCRIPTION
            "The alarm indicating that the AC-side hard pipe bandwidth exceeded the interface bandwidth and became invalid was cleared."
        ::= { hwXQoSNotifications 62 }
--end add by yangting
--begin add by lidapeng
    hwXQoSHardPipeApplySQFailAlarm NOTIFICATION-TYPE
        OBJECTS { hwXQoSHardPipeApplySQFailAlarmIfIndex }
        STATUS current
        DESCRIPTION
            "SQID resource application failure alarm when configuring hard pipe."
        ::= { hwXQoSNotifications 79 }

    hwXQoSHardPipeApplySQFailAlarmClear NOTIFICATION-TYPE
        OBJECTS { hwXQoSHardPipeApplySQFailAlarmIfIndex }
        STATUS current
        DESCRIPTION
            "The alarm of SQID resource application failure was cleared."
        ::= { hwXQoSNotifications 80 }
--end add by lidapeng

--begin add by gaolikun
    hwXQoSTMPerformanceAlarm NOTIFICATION-TYPE
        OBJECTS {
            hwXQoSTMPerformanceAlarmSlotId,
            hwXQoSTMPerformanceAlarmChipId }
        STATUS current
        DESCRIPTION
            "The flow bandwidth usage nearly exceeded the forwarding capability of the TM chip."
        ::= { hwXQoSNotifications 83 }

    hwXQoSTMPerformanceAlarmClear NOTIFICATION-TYPE
        OBJECTS {
            hwXQoSTMPerformanceAlarmSlotId,
            hwXQoSTMPerformanceAlarmChipId }
        STATUS current
        DESCRIPTION
            "The alarm of TM performance was cleared."
        ::= { hwXQoSNotifications 84 }
--end add by gaolikun

--begin add by guohongbo
    hwXQoSModeChannelOverPortShapAlarm NOTIFICATION-TYPE
        OBJECTS { hwXQoSModeChannelOverPortShapAlarmIfIndex }
        STATUS current
        DESCRIPTION
            "The mode channel bandwidth exceeded the port shaping."
        ::= { hwXQoSNotifications 105 }

    hwXQoSModeChannelOverPortShapAlarmClear NOTIFICATION-TYPE
        OBJECTS { hwXQoSModeChannelOverPortShapAlarmIfIndex }
        STATUS current
        DESCRIPTION
            "The alarm indicating that the mode channel bandwidth exceeded the port shaping was cleared."
        ::= { hwXQoSNotifications 106 }
--end add by guohongbo

--begin add by tanyashi
    hwXQoSModeFlexeOverPortShapAlarm NOTIFICATION-TYPE
        OBJECTS { hwXQoSModeFlexeOverPortShapAlarmIfIndex }
        STATUS current
        DESCRIPTION
            "The mode flexe bandwidth exceeded the port shaping."
        ::= { hwXQoSNotifications 136 }

    hwXQoSModeFlexeOverPortShapAlarmClear NOTIFICATION-TYPE
        OBJECTS { hwXQoSModeFlexeOverPortShapAlarmIfIndex }
        STATUS current
        DESCRIPTION
	        "The alarm indicating that the mode flexe bandwidth exceeded the port shaping was cleared."
        ::= { hwXQoSNotifications 137 }
--end add by tanyashi

--begin add by guzhen
    hwXQoSRedirectNextHopInvalidAlarm NOTIFICATION-TYPE
        OBJECTS {
                hwXQoSRedirectNextHopInvalidAlarmBehaviorName,
                hwXQoSRedirectNextHopInvalidAlarmRdrType,
                hwXQoSRedirectNextHopInvalidAlarmInterface }
        STATUS current
        DESCRIPTION
                "The SNMP trap is generated when when the redirect nexthop address did not match the network segment of the outbound interface."
        ::= { hwXQoSNotifications 65 }

    hwXQoSRedirectNextHopInvalidAlarmClear NOTIFICATION-TYPE
        OBJECTS {
                hwXQoSRedirectNextHopInvalidAlarmBehaviorName,
                hwXQoSRedirectNextHopInvalidAlarmRdrType,
                hwXQoSRedirectNextHopInvalidAlarmInterface }
        STATUS current
        DESCRIPTION
                "Clear the SNMP trap is generated when when the redirect nexthop address did not match the network segment of the outbound interface."
        ::= { hwXQoSNotifications 66 }
--end add by guzhen

    hwXACLEPGEnableAlarm NOTIFICATION-TYPE
        OBJECTS {
            hwXACLEPGEnableAlarmSlotid
            }
        STATUS current
        DESCRIPTION
            "The SNMP trap is generated when the traffic-segment enabled failed."
        ::= { hwXQoSNotifications 93}

    hwXACLEPGEnableResume NOTIFICATION-TYPE
        OBJECTS {
            hwXACLEPGEnableAlarmSlotid
            }
        STATUS current
        DESCRIPTION
            "Delete useless acl configuration."
        ::= { hwXQoSNotifications 94}

    hwXACLEPGPolicyAlarm NOTIFICATION-TYPE
        OBJECTS {
            hwXAclEpgPolicyAlarmSourceSegmentId,
            hwXAclEpgPolicyAlarmDestinationSegmentId,
            hwXAclEpgPolicyAlarmProtocol,
            hwXAclEpgPolicyAlarmSourceport,
            hwXAclEpgPolicyAlarmDestinationport,
            hwXAclEpgPolicyAlarmClassifier,
            hwXAclEpgPolicyAlarmSlotid
            }
        STATUS current
        DESCRIPTION
        "The SNMP trap is generated when the EPG policy created failed."
        ::= { hwXQoSNotifications 85}

    hwXACLEPGPolicyResume NOTIFICATION-TYPE
        OBJECTS {
            hwXAclEpgPolicyAlarmSourceSegmentId,
            hwXAclEpgPolicyAlarmDestinationSegmentId,
            hwXAclEpgPolicyAlarmProtocol,
            hwXAclEpgPolicyAlarmSourceport,
            hwXAclEpgPolicyAlarmDestinationport,
            hwXAclEpgPolicyAlarmClassifier,
            hwXAclEpgPolicyAlarmSlotid
            }
        STATUS current
        DESCRIPTION
            "Delete useless acl configuration."
        ::= { hwXQoSNotifications 86}

    hwXACLEPGCreateGroupAlarm NOTIFICATION-TYPE
        OBJECTS {
            hwXACLEPGCreateGroupAlarmSlotid,
            hwXACLEPGCreateGroupAlarmSegmentid
            }
        STATUS current
        DESCRIPTION
            "The SNMP trap is generated when the segment-id created failed."
        ::= { hwXQoSNotifications 87}

    hwXACLEPGCreateGroupResume NOTIFICATION-TYPE
        OBJECTS {
            hwXACLEPGCreateGroupAlarmSlotid,
            hwXACLEPGCreateGroupAlarmSegmentid
            }
        STATUS current
        DESCRIPTION
            "Delete useless acl configuration."
        ::= { hwXQoSNotifications 88}

    hwXACLEPGGroupMemberAlarm NOTIFICATION-TYPE
        OBJECTS {
            hwXAclEpgGroupMemberAlarmIPAddress,
            hwXAclEpgGroupMemberAlarmIPMask,
            hwXAclEpgGroupMemberAlarmVpnInstanceName,
            hwXAclEpgGroupMemberAlarmSegmentId,
            hwXAclEpgGroupMemberAlarmSlotid
            }
        STATUS current
        DESCRIPTION
            "The SNMP trap is generated when the segment-member added failed."
        ::= { hwXQoSNotifications 89}

    hwXACLEPGGroupMemberResume NOTIFICATION-TYPE
        OBJECTS {
            hwXAclEpgGroupMemberAlarmIPAddress,
            hwXAclEpgGroupMemberAlarmIPMask,
            hwXAclEpgGroupMemberAlarmVpnInstanceName,
            hwXAclEpgGroupMemberAlarmSegmentId,
            hwXAclEpgGroupMemberAlarmSlotid
            }
        STATUS current
        DESCRIPTION
            "Delete useless acl configuration."
        ::= { hwXQoSNotifications 90}

    hwXACLEPGGroupMemberV6Alarm NOTIFICATION-TYPE
        OBJECTS {
            hwXAclEpgGroupMemberV6AlarmIPv6Address,
            hwXAclEpgGroupMemberV6AlarmIPv6Mask,
            hwXAclEpgGroupMemberV6AlarmVpnInstanceName,
            hwXAclEpgGroupMemberV6AlarmSegmentId,
            hwXAclEpgGroupMemberV6AlarmSlotid
            }
        STATUS current
        DESCRIPTION
            "The SNMP trap is generated when the segment-member added failed."
        ::= { hwXQoSNotifications 101}

    hwXACLEPGGroupMemberV6Resume NOTIFICATION-TYPE
        OBJECTS {
            hwXAclEpgGroupMemberV6AlarmIPv6Address,
            hwXAclEpgGroupMemberV6AlarmIPv6Mask,
            hwXAclEpgGroupMemberV6AlarmVpnInstanceName,
            hwXAclEpgGroupMemberV6AlarmSegmentId,
            hwXAclEpgGroupMemberV6AlarmSlotid
            }
        STATUS current
        DESCRIPTION
            "Delete useless acl configuration."
        ::= { hwXQoSNotifications 102}

    hwXACLResourceAlarm NOTIFICATION-TYPE
        OBJECTS {
            hwXACLResourceAlarmSlotid,
            hwXACLResourceAlarmServiceType,
            hwXACLResourceAlarmServiceName,
            hwXACLResourceAlarmApplyType,
            hwXACLResourceAlarmInterfaceName,
            hwXACLResourceAlarmDirection,
            hwXACLResourceAlarmServiceParam1,
            hwXACLResourceAlarmServiceParam2,
            hwXACLResourceAlarmServiceParam3,
            hwXACLResourceAlarmACLFailReason
            }
        STATUS current
        DESCRIPTION
            "The service failed to be delivered because ACL resources were insufficient."
        ::= { hwXQoSNotifications 97}

    hwXACLResourceAlarmResume NOTIFICATION-TYPE
        OBJECTS {
            hwXACLResourceAlarmSlotid,
            hwXACLResourceAlarmServiceType,
            hwXACLResourceAlarmServiceName,
            hwXACLResourceAlarmApplyType,
            hwXACLResourceAlarmInterfaceName,
            hwXACLResourceAlarmDirection,
            hwXACLResourceAlarmServiceParam1,
            hwXACLResourceAlarmServiceParam2,
            hwXACLResourceAlarmServiceParam3,
            hwXACLResourceAlarmACLFailReason
            }
        STATUS current
        DESCRIPTION
            "ACL resources are sufficient."
        ::= { hwXQoSNotifications 98}

    hwEnpPerformanceAlarm NOTIFICATION-TYPE
        OBJECTS {
            hwEnpPerformanceAlarmSlotid
            }
        STATUS current
        DESCRIPTION
            "The SNMP trap is generated when the rate at which packets are sent to the built-in chip of the CPU exceeds the processing capability of the chip."
        ::= { hwXQoSNotifications 99}

    hwEnpPerformanceAlarmResume NOTIFICATION-TYPE
        OBJECTS {
            hwEnpPerformanceAlarmSlotid
            }
        STATUS current
        DESCRIPTION
            "The SNMP trap is generated when the rate at which packets are sent to the built-in chip of the CPU is normal."
        ::= { hwXQoSNotifications 100}

    hwXQoSPfcApplyFailAlarm NOTIFICATION-TYPE
        OBJECTS {
            hwXQoSPfcApplyFailAlarmIfName
            }
        STATUS current
        DESCRIPTION
            "The SNMP trap is generated when pfc is failed to apply on interface."
        ::= { hwXQoSNotifications 91 }

    hwXQoSPfcApplyFailAlarmResume NOTIFICATION-TYPE
        OBJECTS {
            hwXQoSPfcApplyFailAlarmIfName
            }
        STATUS current
        DESCRIPTION
            "Clear the SNMP trap which is generated when pfc is failed to apply on interface."
        ::= { hwXQoSNotifications 92 }

    hwXQoSPfcInnerDeadLockAlarm NOTIFICATION-TYPE
        STATUS current
        DESCRIPTION
            "The SNMP trap is generated when detected number of times this time than the last count increased or less than."
        ::= { hwXQoSNotifications 103}

    hwXQoSPfcInnerDeadLockResume NOTIFICATION-TYPE
        STATUS current
        DESCRIPTION
            "Clear the SNMP trap which is generated when detected number this time is not increased than the last count."
        ::= { hwXQoSNotifications 104}

    hwXQoSResourceAlarm NOTIFICATION-TYPE
        OBJECTS {
            hwXQoSResourceAlarmSlotID,
            hwXQoSResourceAlarmType,
            hwXQoSResourceAlarmServiceType
            }
        STATUS current
        DESCRIPTION
            "Services fail to be delivered due to insufficient resources."
        ::= { hwXQoSNotifications 107 }

    hwXQoSResourceResume NOTIFICATION-TYPE
        OBJECTS {
            hwXQoSResourceAlarmSlotID,
            hwXQoSResourceAlarmType,
            hwXQoSResourceAlarmServiceType
            }
        STATUS current
        DESCRIPTION
            "Resources are sufficient."
        ::= { hwXQoSNotifications 108 }

    hwXQoSResourceOverrunAlarm NOTIFICATION-TYPE
        OBJECTS {
            hwXQoSResourceOverrunAlarmSlotID,
            hwXQoSResourceOverrunAlarmType,
            hwXQoSResourceOverrunAlarmTotal,
            hwXQoSResourceOverrunAlarmFree,
            hwXQoSResourceOverrunAlarmThreshold
            }
        STATUS current
        DESCRIPTION
            "The resource usage exceeds the alarm threshold."
        ::= { hwXQoSNotifications 109 }

    hwXQoSResourceOverrunResume NOTIFICATION-TYPE
        OBJECTS {
            hwXQoSResourceOverrunAlarmSlotID,
            hwXQoSResourceOverrunAlarmType,
            hwXQoSResourceOverrunAlarmTotal,
            hwXQoSResourceOverrunAlarmFree,
            hwXQoSResourceOverrunAlarmThreshold
            }
        STATUS current
        DESCRIPTION
            "The resource usage is lower than the alarm threshold."
        ::= { hwXQoSNotifications 110 }

--begin add by guanqingyu
    hwXQoSUnsupportedFeatureAlarm NOTIFICATION-TYPE
        OBJECTS {
                hwXQoSUnsupportedFeatureAlarmBoardID,
                hwXQoSUnsupportedFeatureAlarmFeatureType }
        STATUS current
        DESCRIPTION
        "The SNMP trap is generated when the qos configurations not support current board."
        ::= { hwXQoSNotifications 113 }

    hwXQoSUnsupportedFeatureAlarmResume NOTIFICATION-TYPE
        OBJECTS {
                hwXQoSUnsupportedFeatureAlarmBoardID,
                hwXQoSUnsupportedFeatureAlarmFeatureType }
        STATUS current
        DESCRIPTION
        "Clear the SNMP trap is generated when unsupported qos configurations are deleted."
        ::= { hwXQoSNotifications 114 }
--end add by guanqingyu

    hwXQoSBUMReplicationAlarm NOTIFICATION-TYPE
        OBJECTS {
            hwXQoSBUMReplicationAlarmSlotId,
            hwXQoSBUMReplicationAlarmChipId
            }
        STATUS current
        DESCRIPTION
            "The BUM traffic to be replicated exceeds the device capability."
        ::= { hwXQoSNotifications 115 }

    hwXQoSBUMReplicationResume NOTIFICATION-TYPE
        OBJECTS {
            hwXQoSBUMReplicationAlarmSlotId,
            hwXQoSBUMReplicationAlarmChipId
            }
        STATUS current
        DESCRIPTION
            "The BUM traffic to be replicated falls below the device capability."
        ::= { hwXQoSNotifications 116 }

    hwXQoSVlanStormSuppressAlarm NOTIFICATION-TYPE
        OBJECTS {
                hwXQoSVlanStormSuppressAlarmVlanid
                }
        STATUS current
        DESCRIPTION
            "The SNMP trap is generated when the vlan has dropped packets because of storm suppress."
        ::= { hwXQoSNotifications 117}

    hwXQoSVlanStormSuppressAlarmResume NOTIFICATION-TYPE
        OBJECTS {
                hwXQoSVlanStormSuppressAlarmVlanid
                }
        STATUS current
        DESCRIPTION
            "The SNMP trap is generated when the vlan is recovered from dropped packets because of storm suppress."
        ::= { hwXQoSNotifications 118}

    hwXQoSBDStormSuppressAlarm NOTIFICATION-TYPE
        OBJECTS {
            hwXQoSBDStormSuppressAlarmBdid
            }
        STATUS current
        DESCRIPTION
            "The SNMP trap is generated when the bridge-domain has dropped packets because of storm suppress."
        ::= { hwXQoSNotifications 119}

    hwXQoSBDStormSuppressAlarmResume NOTIFICATION-TYPE
        OBJECTS {
            hwXQoSBDStormSuppressAlarmBdid
            }
        STATUS current
        DESCRIPTION
            "The SNMP trap is generated when the bridge-domain is recovered from dropped packets because of storm suppress."
        ::= { hwXQoSNotifications 120}

    hwXQoSInterfaceDownRedirectNextHopInvalidAlarm NOTIFICATION-TYPE
        OBJECTS {
            hwXQoSInterfaceDownRedirectNextHopInvalidAlarmRdrType,
            hwXQoSInterfaceDownRedirectNextHopInvalidAlarmSlotID,
            hwXQoSInterfaceDownRedirectNextHopInvalidAlarmInterface,
            hwXQoSInterfaceDownRedirectNextHopInvalidAlarmBehaviorName
            }
        STATUS current
        DESCRIPTION
            "The SNMP trap is generated when the interface goes down and the redirection next hop becomes invalid."
        ::= { hwXQoSNotifications 121}

    hwXQoSInterfaceDownRedirectNextHopInvalidAlarmClear NOTIFICATION-TYPE
        OBJECTS {
            hwXQoSInterfaceDownRedirectNextHopInvalidAlarmRdrType,
            hwXQoSInterfaceDownRedirectNextHopInvalidAlarmSlotID,
            hwXQoSInterfaceDownRedirectNextHopInvalidAlarmInterface
            }
        STATUS current
        DESCRIPTION
            "The SNMP trap is generated when the interface goes up or the redirection next hop configuration is deleted."
        ::= { hwXQoSNotifications 122 }

    hwXQoSRedirectNextHopEventLog NOTIFICATION-TYPE
        OBJECTS {
            hwXQoSRedirectNextHopEventLogSlotId,
            hwXQoSRedirectNextHopEventLogRdrType,
            hwXQoSRedirectNextHopEventLogIpAddress,
            hwXQoSRedirectNextHopEventLogBehaviorName
            }
        STATUS current
        DESCRIPTION
            "The SNMP trap is generated when route switching in scenarios where a redirection policy with no outbound interface specified is deployed."
        ::= { hwXQoSNotifications 123 }

    hwXQoSBgpFlowspecDestinationOriginAsOverAlarm NOTIFICATION-TYPE
        STATUS current
        DESCRIPTION
            "The SNMP trap is generated when the number of BGP FlowSpec rules matching the start AS (Origin-AS) of the destination IP address reaches the upper limit."
        ::= { hwXQoSNotifications 124 }
    hwXQoSBgpFlowspecDestinationOriginAsOverAlarmClear NOTIFICATION-TYPE
        STATUS current
        DESCRIPTION
            "The SNMP trap is generated when delete excess BGP FlowSpec rules matching the start AS of the destination IP address."
        ::= { hwXQoSNotifications 125 }

    hwXQoSUserQueueApplyPirExhaustionAlarm NOTIFICATION-TYPE
        OBJECTS {
            hwXQoSUserQueueApplyPirExhaustionAlarmSlotId,
            hwXQoSUserQueueApplyPirExhaustionAlarmTmChipId,
            hwXQoSUserQueueApplyPirExhaustionAlarmPoolIndex
            }
        STATUS current
        DESCRIPTION
            "The sum of the PIRs requested by all users from the resource pool exceeded the maximum configuration specification of the TM chip."
        ::= { hwXQoSNotifications 128 }

    hwXQoSUserQueueApplyPirExhaustionResume NOTIFICATION-TYPE
        OBJECTS {
            hwXQoSUserQueueApplyPirExhaustionAlarmSlotId,
            hwXQoSUserQueueApplyPirExhaustionAlarmTmChipId,
            hwXQoSUserQueueApplyPirExhaustionAlarmPoolIndex
            }
        STATUS current
        DESCRIPTION
            "The alarm is cleared when the sum of PIRs requested by all users from the resource pool falls below the maximum configuration of the TM chip."
        ::= { hwXQoSNotifications 129 }

    hwXQoSUserQueueApplyPirPreAlarm NOTIFICATION-TYPE
        OBJECTS {
            hwXQoSUserQueueApplyPirPreAlarmSlotId,
            hwXQoSUserQueueApplyPirPreAlarmTmChipId,
            hwXQoSUserQueueApplyPirPreAlarmPoolIndex
            }
        STATUS current
        DESCRIPTION
            "The sum of the PIRs requested by all users from the resource pool exceeded 90% of the maximum configuration specification of the TM chip."
        ::= { hwXQoSNotifications 130 }

    hwXQoSUserQueueApplyPirPreResume NOTIFICATION-TYPE
        OBJECTS {
            hwXQoSUserQueueApplyPirPreAlarmSlotId,
            hwXQoSUserQueueApplyPirPreAlarmTmChipId,
            hwXQoSUserQueueApplyPirPreAlarmPoolIndex
            }
        STATUS current
        DESCRIPTION
            "This alarm is cleared when the sum of PIRs requested by all users from the resource pool is less than 90% of the maximum configuration of the TM chip."
        ::= { hwXQoSNotifications 131 }

    hwXQoSUserQueuePirAdjustAlarm NOTIFICATION-TYPE
        OBJECTS {
            hwXQoSUserQueuePirAdjustAlarmSlotId,
            hwXQoSUserQueuePirAdjustAlarmTmChipId,
            hwXQoSUserQueuePirAdjustAlarmPoolIndex
            }
        STATUS current
        DESCRIPTION
            "When the user-queue PIR applied for by all users exceeds the threshold, bandwidth adjustment is triggered. During the adjustment, packet loss may occur."
        ::= { hwXQoSNotifications 132 }

    hwXQoSUserQueuePirAdjustResume NOTIFICATION-TYPE
        OBJECTS {
            hwXQoSUserQueuePirAdjustAlarmSlotId,
            hwXQoSUserQueuePirAdjustAlarmTmChipId,
            hwXQoSUserQueuePirAdjustAlarmPoolIndex
            }
        STATUS current
        DESCRIPTION
            "Bandwidth adjustment is canceled when the user-queue PIR bandwidth applied for by all users is lower than the threshold."
        ::= { hwXQoSNotifications 133 }

--begin
        hwXQoSUnsupportedActionAlarm NOTIFICATION-TYPE
            OBJECTS {
                hwXQoSUnsupportedActionAlarmSlotId,
                hwXQoSUnsupportedActionAlarmActionName,
                hwXQoSUnsupportedActionAlarmDirection
                }
            STATUS current
            DESCRIPTION
            "Actions in a traffic behavior for ACL will not take effect on the current board."
            ::= { hwXQoSNotifications 134 }

        hwXQoSUnsupportedActionResume NOTIFICATION-TYPE
            OBJECTS {
                hwXQoSUnsupportedActionAlarmSlotId,
                hwXQoSUnsupportedActionAlarmActionName,
                hwXQoSUnsupportedActionAlarmDirection
                }
            STATUS current
            DESCRIPTION
            "The alarm is cleared when an unsupported action is deleted from traffic behavior."
            ::= { hwXQoSNotifications 135 }
--end
--begin
    hwXQoSCarBindwidthExceedChipLimitAlarm NOTIFICATION-TYPE
        OBJECTS {
            hwXQoSCarBindwidthExceedChipLimitAlarmSlotId,
            hwXQoSCarBindwidthExceedChipLimitAlarmCarType,
            hwXQoSCarBindwidthExceedChipLimitAlarmCir,
            hwXQoSCarBindwidthExceedChipLimitAlarmPir,
            hwXQoSCarBindwidthExceedChipLimitAlarmMaxRateLimit,
            hwXQoSCarBindwidthExceedChipLimitAlarmIsPercent
            }
        STATUS current
        DESCRIPTION
            "The bandwidth configured for CAR exceeds the rate limiting capability of the chip."
        ::= { hwXQoSNotifications 144 }

    hwXQoSCarBindwidthExceedChipLimitResume NOTIFICATION-TYPE
        OBJECTS {
            hwXQoSCarBindwidthExceedChipLimitAlarmSlotId,
            hwXQoSCarBindwidthExceedChipLimitAlarmCarType,
            hwXQoSCarBindwidthExceedChipLimitAlarmCir,
            hwXQoSCarBindwidthExceedChipLimitAlarmPir,
            hwXQoSCarBindwidthExceedChipLimitAlarmMaxRateLimit,
            hwXQoSCarBindwidthExceedChipLimitAlarmIsPercent
            }
        STATUS current
        DESCRIPTION
            "The alarm is cleared when current car configuration bandwidth belows the rate limiting capability of the chip."
        ::= { hwXQoSNotifications 145 }
--end
--begin
    hwXQoSModeChannelOverEthBnBwdAlarm NOTIFICATION-TYPE
        OBJECTS {
            hwXQoSModeChannelOverEthBnBwdAlarmGroupName,
            hwXQoSModeChannelOverEthBnBwdAlarmEthBnSubInterface
            }
        STATUS current
        DESCRIPTION
            "The bandwidth sum of channelized sub-interfaces in an interface group is greater than or equal to the ETH-BN bandwidth."
        ::= { hwXQoSNotifications 146 }

    hwXQoSModeChannelOverEthBnBwdResume NOTIFICATION-TYPE
        OBJECTS {
            hwXQoSModeChannelOverEthBnBwdAlarmGroupName,
            hwXQoSModeChannelOverEthBnBwdAlarmEthBnSubInterface
            }
        STATUS current
        DESCRIPTION
            "The bandwidth sum of sliced sub-interfaces in an interface group is less than the ETH-BN bandwidth."
        ::= { hwXQoSNotifications 147 }
--end
--begin
    hwXACLEPGRuleAlarm NOTIFICATION-TYPE
        OBJECTS {
            hwXACLEPGRuleAlarmSlotid,
            hwXACLEPGRuleAlarmPolicy,
            hwXACLEPGRuleAlarmClassifier,
            hwXACLEPGRuleAlarmPriority,
            hwXACLEPGRuleAlarmSourceSegmentId,
            hwXACLEPGRuleAlarmDestinationSegmentId,
            hwXACLEPGRuleAlarmProtocol,
            hwXACLEPGRuleAlarmSourceport,
            hwXACLEPGRuleAlarmDestinationport
            }
        STATUS current
        DESCRIPTION
            "The SNMP trap is generated when the GBP rule added failed."
        ::= { hwXQoSNotifications 148}

    hwXACLEPGRuleResume NOTIFICATION-TYPE
        OBJECTS {
            hwXACLEPGRuleAlarmSlotid,
            hwXACLEPGRuleAlarmPolicy,
            hwXACLEPGRuleAlarmClassifier,
            hwXACLEPGRuleAlarmPriority,
            hwXACLEPGRuleAlarmSourceSegmentId,
            hwXACLEPGRuleAlarmDestinationSegmentId,
            hwXACLEPGRuleAlarmProtocol,
            hwXACLEPGRuleAlarmSourceport,
            hwXACLEPGRuleAlarmDestinationport
            }
        STATUS current
        DESCRIPTION
            "Delete useless acl configuration."
        ::= { hwXQoSNotifications 149}
--end
--begin
    hwXQoSBoardHQoSFailAlarm NOTIFICATION-TYPE
        OBJECTS {
            hwXQoSBoardHQoSFailAlarmServiceType,
            hwXQoSBoardHQoSFailAlarmSlotId,
            hwXQoSBoardHQoSFailAlarmReasonId,
            hwXQoSBoardHQoSFailAlarmReasonDescription
            }
        STATUS current
        DESCRIPTION
            "Some HQoS functions on the board do not take effect."
        ::= { hwXQoSNotifications 150 }

    hwXQoSBoardHQoSFailResume NOTIFICATION-TYPE
        OBJECTS {
            hwXQoSBoardHQoSFailAlarmServiceType,
            hwXQoSBoardHQoSFailAlarmSlotId,
            hwXQoSBoardHQoSFailAlarmReasonId,
            hwXQoSBoardHQoSFailAlarmReasonDescription
            }
        STATUS current
        DESCRIPTION
            "The alarm is cleared when the unsupported HQoS service is processed."
        ::= { hwXQoSNotifications 151 }
--end
--begin
    hwXQoSInterfaceHQoSFailAlarm NOTIFICATION-TYPE
        OBJECTS {
            hwXQoSInterfaceHQoSFailAlarmServiceType,
            hwXQoSInterfaceHQoSFailAlarmSlotId,
            hwXQoSInterfaceHQoSFailAlarmInterfaceName,
            hwXQoSInterfaceHQoSFailAlarmReasonId
            }
        STATUS current
        DESCRIPTION
            "Some HQoS functions on the port do not take effect."
        ::= { hwXQoSNotifications 152 }

    hwXQoSInterfaceHQoSFailResume NOTIFICATION-TYPE
        OBJECTS {
            hwXQoSInterfaceHQoSFailAlarmServiceType,
            hwXQoSInterfaceHQoSFailAlarmSlotId,
            hwXQoSInterfaceHQoSFailAlarmInterfaceName,
            hwXQoSInterfaceHQoSFailAlarmReasonId
            }
        STATUS current
        DESCRIPTION
            "The alarm is cleared when the unsupported HQoS service is processed."
        ::= { hwXQoSNotifications 153 }
--end
--begin
    hwXQoSReceivedMultiPauseFrameInterfaceDownAlarm NOTIFICATION-TYPE
        OBJECTS {
            hwXQoSReceivedMultiPauseFrameInterfaceDownAlarmInterfaceName
            }
        STATUS current
        DESCRIPTION
        "The interface line protocol is down after received too many PAUSE frames in a short time."
        ::= { hwXQoSNotifications 154 }

    hwXQoSReceivedMultiPauseFrameInterfaceDownResume NOTIFICATION-TYPE
        OBJECTS {
            hwXQoSReceivedMultiPauseFrameInterfaceDownAlarmInterfaceName
            }
        STATUS current
        DESCRIPTION
        "The interface line protocol recovery up after received not too many PAUSE frames in a short time."
        ::= { hwXQoSNotifications 155 }
--end
--begin
    hwXQoSTrunkTrafficCongestionAlarm NOTIFICATION-TYPE
        OBJECTS {
            hwXQoSTrunkTrafficCongestionAlarmTrunkName,
            hwXQoSTrunkTrafficCongestionAlarmSlotId
            }
        STATUS current
        DESCRIPTION
            "Traffic congestion occurs on the trunk interface, and traffic on all member interfaces may be affected."
        ::= { hwXQoSNotifications 156 }

    hwXQoSTrunkTrafficCongestionResume NOTIFICATION-TYPE
        OBJECTS {
            hwXQoSTrunkTrafficCongestionAlarmTrunkName,
            hwXQoSTrunkTrafficCongestionAlarmSlotId
            }
        STATUS current
        DESCRIPTION
            "Traffic congestion on the trunk interface is cleared, and traffic on the member interface recovers."
        ::= { hwXQoSNotifications 157 }
--end
--begin
    hwXQoSFwdResourceOverload NOTIFICATION-TYPE
        OBJECTS {
            hwXQoSFwdResourceOverloadSlotId,
            hwXQoSFwdResourceOverloadReasonId
            }
        STATUS current
        DESCRIPTION
            "The board forwarding engine resources were overload."
        ::= { hwXQoSNotifications 158 }

    hwXQoSFwdResourceOverloadResume NOTIFICATION-TYPE
        OBJECTS {
            hwXQoSFwdResourceOverloadSlotId,
            hwXQoSFwdResourceOverloadReasonId
            }
        STATUS current
        DESCRIPTION
            "The alarm is cleared when the board forwarding engine resources overload is recovered."
        ::= { hwXQoSNotifications 159 }
--end
--begin
    hwXQoSBoardServiceMismatchEvent NOTIFICATION-TYPE
        OBJECTS {
            hwXQoSBoardServiceMismatchEventEntityPhysicalIndex,
            hwXQoSBoardServiceMismatchEventServiceID,
            hwXQoSBoardServiceMismatchEventEntPhysicalName,
            hwXQoSBoardServiceMismatchEventServiceName,
            hwXQoSBoardServiceMismatchEventPrecautions
            }
        STATUS current
        DESCRIPTION
            "The service is not supported for the board hardware."
        ::= { hwXQoSNotifications 160 }
--end
--begin
    hwXQoSSlotTrafficCongestionAlarm NOTIFICATION-TYPE
        OBJECTS {
            hwXQoSSlotTrafficCongestionAlarmSlotId
            }
        STATUS current
        DESCRIPTION
            "Traffic congestion occurs on the slot, and traffic on all interfaces of the slot may be affected."
        ::= { hwXQoSNotifications 161 }

    hwXQoSSlotTrafficCongestionResume NOTIFICATION-TYPE
        OBJECTS {
            hwXQoSSlotTrafficCongestionAlarmSlotId
            }
        STATUS current
        DESCRIPTION
            "Traffic congestion on the slot is cleared, and traffic on the slot recovers."
        ::= { hwXQoSNotifications 162 }
--end
--begin
    hwXQoSChipBufferOverrunAlarm NOTIFICATION-TYPE
        OBJECTS {
            hwXQoSChipBufferOverrunAlarmSlotId,
            hwXQoSChipBufferOverrunAlarmChipId,
            hwXQoSChipBufferOverrunAlarmUsedLength,
            hwXQoSChipBufferOverrunAlarmThreshold
            }
        STATUS current
        DESCRIPTION
            "The SNMP trap is generated when chip buffer is overrun."
        ::= { hwXQoSNotifications 163 }
    hwXQoSChipBufferOverrunResume NOTIFICATION-TYPE
        OBJECTS {
            hwXQoSChipBufferOverrunAlarmSlotId,
            hwXQoSChipBufferOverrunAlarmChipId,
            hwXQoSChipBufferOverrunAlarmUsedLength,
            hwXQoSChipBufferOverrunAlarmThreshold
            }
        STATUS current
        DESCRIPTION
            "Clear the SNMP trap which is generated when chip buffer is no longer overrun."
        ::= { hwXQoSNotifications 164 }

    hwXACLEPGGroupMemberMacVlanAlarm NOTIFICATION-TYPE
        OBJECTS {
            hwXAclEpgGroupMemberMacAlarmMacAddress,
            hwXAclEpgGroupMemberMacAlarmVlanId,
            hwXAclEpgGroupMemberMacAlarmSegmentId,
            hwXAclEpgGroupMemberMacAlarmSlotid
            }
        STATUS current
        DESCRIPTION
            "The SNMP trap is generated when the VLAN and MAC address-based segment-member added failed."
        ::= { hwXQoSNotifications 174 }

    hwXACLEPGGroupMemberMacVlanResume NOTIFICATION-TYPE
        OBJECTS {
            hwXAclEpgGroupMemberMacAlarmMacAddress,
            hwXAclEpgGroupMemberMacAlarmVlanId,
            hwXAclEpgGroupMemberMacAlarmSegmentId,
            hwXAclEpgGroupMemberMacAlarmSlotid
            }
        STATUS current
        DESCRIPTION
            "The SNMP trap is generated when the VLAN and MAC address-based segment-member resume."
        ::= { hwXQoSNotifications 175 }

    hwXACLEPGGroupMemberMacBdAlarm NOTIFICATION-TYPE
        OBJECTS {
            hwXAclEpgGroupMemberMacAlarmMacAddress,
            hwXAclEpgGroupMemberMacAlarmBdId,
            hwXAclEpgGroupMemberMacAlarmSegmentId,
            hwXAclEpgGroupMemberMacAlarmSlotid
            }
        STATUS current
        DESCRIPTION
            "The SNMP trap is generated when the bridge-domain and MAC address-based segment-member added failed."
        ::= { hwXQoSNotifications 176 }

    hwXACLEPGGroupMemberMacBdResume NOTIFICATION-TYPE
        OBJECTS {
            hwXAclEpgGroupMemberMacAlarmMacAddress,
            hwXAclEpgGroupMemberMacAlarmBdId,
            hwXAclEpgGroupMemberMacAlarmSegmentId,
            hwXAclEpgGroupMemberMacAlarmSlotid
            }
        STATUS current
        DESCRIPTION
            "The SNMP trap is generated when the bridge-domain and MAC address-based segment-member resume."
        ::= { hwXQoSNotifications 177 }

    hwXACLEPGPolicyApplyAlarm NOTIFICATION-TYPE
        OBJECTS {
            hwXACLEPGAlarmSlotid,
            hwXACLEPGAlarmView,
            hwXACLEPGAlarmPolicy
            }
        STATUS current
        DESCRIPTION
            "The SNMP trap is generated when the traffic-segment policy applied failed."
        ::= { hwXQoSNotifications 188 }
    hwXACLEPGPolicyApplyResume NOTIFICATION-TYPE
        OBJECTS {
            hwXACLEPGAlarmSlotid,
            hwXACLEPGAlarmView,
            hwXACLEPGAlarmPolicy
            }
        STATUS current
        DESCRIPTION
            "The SNMP trap is generated when the traffic-segment policy applied resume."
        ::= { hwXQoSNotifications 189 }

    hwXACLEPGPbrInvalidAlarm NOTIFICATION-TYPE
        OBJECTS {
            hwXACLEPGAlarmRouteTemplate
            }
        STATUS current
        DESCRIPTION
            "The SNMP trap is generated when the PBR of microsegmentation becomes invalid."
        ::= { hwXQoSNotifications 190 }
    hwXACLEPGPbrInvalidResume NOTIFICATION-TYPE
        OBJECTS {
            hwXACLEPGAlarmRouteTemplate
            }
        STATUS current
        DESCRIPTION
            "The SNMP trap is generated when the PBR of microsegmentation resume."
        ::= { hwXQoSNotifications 191 }
--end
--begin
    hwXQoSFlowspecNotSupportBoardEvent NOTIFICATION-TYPE
        OBJECTS {
            hwXQoSFlowspecNotSupportBoardEventChassisID,
            hwXQoSFlowspecNotSupportBoardEventSlotID,
            hwXQoSFlowspecNotSupportBoardEventRuleType,
            hwXQoSFlowspecNotSupportBoardEventAddrType,
            hwXQoSFlowspecNotSupportBoardEventServiceType
            }
        STATUS current
        DESCRIPTION
            "The rule configured for the BGP FlowSpec route is not supported on the board."
        ::= { hwXQoSNotifications 173 }
--end
--begin
    hwXQoSBgpFlowspecDestinationOriginAsOverIPv6Alarm NOTIFICATION-TYPE
        STATUS current
        DESCRIPTION
            "The SNMP trap is generated when the number of BGP FlowSpec rules matching the start AS (Origin-AS) of the destination IPv6 address reaches the upper limit."
        ::= { hwXQoSNotifications 178 }
    hwXQoSBgpFlowspecDestinationOriginAsOverIPv6AlarmClear NOTIFICATION-TYPE
        STATUS current
        DESCRIPTION
            "The SNMP trap is generated when delete excess BGP FlowSpec rules matching the start AS of the destination IPv6 address."
        ::= { hwXQoSNotifications 179 }
--end
--begin
    hwXQoSBgpFlowspecDestinationCommunityOverAlarm NOTIFICATION-TYPE
        OBJECTS {
            hwXQoSBgpFlowspecDestinationCommunityOverAlarmAddrFamily
            }
        STATUS current
        DESCRIPTION
            "The SNMP trap is generated when the number of BGP FlowSpec rules matching the community of the destination IPv6 address reaches the upper limit."
        ::= { hwXQoSNotifications 180 }
    hwXQoSBgpFlowspecDestinationCommunityOverAlarmClear NOTIFICATION-TYPE
        OBJECTS {
            hwXQoSBgpFlowspecDestinationCommunityOverAlarmAddrFamily
            }
        STATUS current
        DESCRIPTION
            "The SNMP trap is generated when delete excess BGP FlowSpec rules matching the community of the destination IPv6 address."
        ::= { hwXQoSNotifications 181 }
--end
--begin
    hwXQoSTrafficPolicyRuleResoucePreAlarm NOTIFICATION-TYPE
        OBJECTS {
            hwXQoSTrafficPolicyRuleResoucePreAlarmSlotId,
            hwXQoSTrafficPolicyRuleResoucePreAlarmThreshold,
            hwXQoSTrafficPolicyRuleResoucePreAlarmReasonId
            }
        STATUS current
        DESCRIPTION
            "The usage of MF classification rules exceeded the pre-warning threshold."
        ::= { hwXQoSNotifications 182 }
    hwXQoSTrafficPolicyRuleResoucePreAlarmResume NOTIFICATION-TYPE
        OBJECTS {
            hwXQoSTrafficPolicyRuleResoucePreAlarmSlotId,
            hwXQoSTrafficPolicyRuleResoucePreAlarmThreshold,
            hwXQoSTrafficPolicyRuleResoucePreAlarmReasonId
            }
        STATUS current
        DESCRIPTION
            "The usage of MF classification rules fell below the pre-warning threshold."
        ::= { hwXQoSNotifications 183 }
--end
--begin
    hwXQoSFLowMatrixRailInvalidAlarm NOTIFICATION-TYPE
        OBJECTS {
            hwXQoSFLowMatrixRailSlotId,
            hwXQoSFLowMatrixRailSourceIp,
            hwXQoSFLowMatrixRailDestinationIp,
            hwXQoSFLowMatrixRailOutPort
            }
        STATUS current
        DESCRIPTION
            "Path planning failed."
        ::= { hwXQoSNotifications 184 }
    hwXQoSFLowMatrixRailInvalidAlarmResume NOTIFICATION-TYPE
        OBJECTS {
            hwXQoSFLowMatrixRailSlotId,
            hwXQoSFLowMatrixRailSourceIp,
            hwXQoSFLowMatrixRailDestinationIp,
            hwXQoSFLowMatrixRailOutPort
            }
        STATUS current
        DESCRIPTION
            "The path planning has been restored."
        ::= { hwXQoSNotifications 185 }
--end
--begin
    hwXQoSBgpFlowspecDDoSLowPriorityAlarm NOTIFICATION-TYPE
        OBJECTS {
            hwXQoSBgpFlowspecDDoSLowPriorityAlarmSlotId,
            hwXQoSBgpFlowspecDDoSLowPriorityAlarmReasonId
            }
        STATUS current
        DESCRIPTION
            "The priority of the BGP FlowSpec DDoS ACL rule is lower than that of the common BGP FlowSpec rule."
        ::= { hwXQoSNotifications 186 }
    hwXQoSBgpFlowspecDDoSLowPriorityAlarmClear NOTIFICATION-TYPE
        OBJECTS {
            hwXQoSBgpFlowspecDDoSLowPriorityAlarmSlotId,
            hwXQoSBgpFlowspecDDoSLowPriorityAlarmReasonId
            }
        STATUS current
        DESCRIPTION
            "The priority of the BGP FlowSpec DDoS ACL rule is not lower than that of the common BGP FlowSpec rule."
        ::= { hwXQoSNotifications 187 }
--end

    hwXQoSGeneral OBJECT IDENTIFIER ::= { hwXQoSObjects 12 }

    hwXQoSFrameId  OBJECT-TYPE
        SYNTAX Integer32
        MAX-ACCESS read-only
        STATUS current
        DESCRIPTION "The ID of the frame."
        ::= { hwXQoSGeneral  1 }

    hwXQoSSlotId  OBJECT-TYPE
        SYNTAX Integer32
        MAX-ACCESS read-only
        STATUS current
        DESCRIPTION "The ID of the slot that the interface is located."
        ::= { hwXQoSGeneral  2 }

    hwXQoSPortId  OBJECT-TYPE
        SYNTAX Integer32
        MAX-ACCESS read-only
        STATUS current
        DESCRIPTION "The ID of the port"
        ::= { hwXQoSGeneral  3 }

    hwXQoSTrapIfName  OBJECT-TYPE
        SYNTAX OCTET STRING (SIZE (1..31))
        MAX-ACCESS read-only
        STATUS current
        DESCRIPTION "The name of the interface."
        ::= { hwXQoSGeneral  4 }

    hwXQoSTrapQueueId  OBJECT-TYPE
        SYNTAX  Integer32
        MAX-ACCESS read-only
        STATUS current
        DESCRIPTION "The ID of the queue giving an alarm."
        ::= { hwXQoSGeneral  5 }


    hwXQoSTrapDiscardPackets  OBJECT-TYPE
        SYNTAX  Counter64
        MAX-ACCESS read-only
        STATUS current
        DESCRIPTION "The number of the discarded packets."
        ::= { hwXQoSGeneral  6 }

    hwXQoSStormControlObjects OBJECT IDENTIFIER ::= { hwXQoSObjects 13 }

    hwXQoSStormControlTable OBJECT-TYPE
        SYNTAX SEQUENCE OF HwXQoSStormControlEntry
        MAX-ACCESS not-accessible
        STATUS current
        DESCRIPTION
            "A Table about storm-control configuration information."
        ::= { hwXQoSStormControlObjects 1 }


    hwXQoSStormControlEntry OBJECT-TYPE
        SYNTAX HwXQoSStormControlEntry
        MAX-ACCESS not-accessible
        STATUS current
        DESCRIPTION
            "Description."
        INDEX { hwXQoSStormControlIfIndex, hwXQoSStormControlType }
        ::= { hwXQoSStormControlTable 1 }


    HwXQoSStormControlEntry ::=
        SEQUENCE {
            hwXQoSStormControlIfIndex
                InterfaceIndex,
            hwXQoSStormControlBroadcastMinRate
                Integer32,
            hwXQoSStormControlBroadcastMaxRate
                Integer32,
            hwXQoSStormControlMulticastMinRate
                Integer32,
            hwXQoSStormControlMulticastMaxRate
                Integer32,
            hwXQoSStormControlAction
                INTEGER,
            hwXQoSStormControlInterval
                Integer32,
            hwXQoSStormControlTrapEnable
                EnabledStatus,
            hwXQoSStormControlLogEnable
                EnabledStatus,
            hwXQoSStormControlStatus
                INTEGER,
            hwXQoSStormControlUnicastMinRate
                Integer32,
            hwXQoSStormControlUnicastMaxRate
                Integer32,
            hwXQoSStormControlBcMode
                INTEGER,
            hwXQoSStormControlMcMode
                INTEGER,
            hwXQoSStormControlUcMode
                INTEGER,
            hwXQoSStormControlIfName
                OCTET STRING,
            hwXQoSStormControlUnknownUnicastMinRate
                Integer32,
            hwXQoSStormControlUnknownUnicastMaxRate
                Integer32,
            hwXQoSStormControlUnknownUcMode
                INTEGER,
            hwXQoSStormControlActionName
                OCTET STRING,
            hwXQoSStormControlType
                OCTET STRING,
            hwXQoSStormControlThreshold
                Integer32,
            hwXQoSStormControlMode
                OCTET STRING,
            hwXQoSStormControlBroadcastRate
                Integer32,
            hwXQoSStormControlMulticastRate
                Integer32,
            hwXQoSStormControlUnicastRate
                Integer32
            }

    hwXQoSStormControlIfIndex OBJECT-TYPE
        SYNTAX InterfaceIndex
        MAX-ACCESS accessible-for-notify
        STATUS current
        DESCRIPTION
            "The interface index, equal to ifIndex."
        ::= { hwXQoSStormControlEntry 1 }

    hwXQoSStormControlBroadcastMinRate OBJECT-TYPE
        SYNTAX Integer32 (0..14881000)
        MAX-ACCESS read-write
        STATUS current
        DESCRIPTION
            "The low water mark of broadcast packets rate. Unit: pps (packets per second).
            zero : storm-control function is not enable for broadcast packets."
        DEFVAL { 0 }
        ::= { hwXQoSStormControlEntry 2 }

    hwXQoSStormControlBroadcastMaxRate OBJECT-TYPE
        SYNTAX Integer32 (0..14881000)
        MAX-ACCESS read-write
        STATUS current
        DESCRIPTION
            "The high water mark of broadcast packets rate. Unit: pps (packets per second).
            zero : storm-control function is not enable for broadcast packets."
        DEFVAL { 0 }
        ::= { hwXQoSStormControlEntry 3 }


    hwXQoSStormControlMulticastMinRate OBJECT-TYPE
        SYNTAX Integer32 (0..14881000)
        MAX-ACCESS read-write
        STATUS current
        DESCRIPTION
            "The low water mark of multicast packets rate. Unit: pps (packets per second).
            zero: storm-control function is not enable for multicast packets."
        DEFVAL { 0 }
        ::= { hwXQoSStormControlEntry 4 }


    hwXQoSStormControlMulticastMaxRate OBJECT-TYPE
        SYNTAX Integer32 (0..14881000)
        MAX-ACCESS read-write
        STATUS current
        DESCRIPTION
            "The high water mark of multicast packets rate. Unit: pps (packets per second).
            zero: storm-control function is not enable for multicast packets."
        DEFVAL { 0 }
        ::= { hwXQoSStormControlEntry 5 }


    hwXQoSStormControlAction OBJECT-TYPE
        SYNTAX INTEGER
            {
            none(1),
            block(2),
            shutdown(3)
            }
        MAX-ACCESS read-write
        STATUS current
        DESCRIPTION
            "storm-control action.
            none : no action will be taken.
            block: packets will be blocked if receiving-rate is higher than the high water mark and will be unblocked only when the receiving-rate drops below the low water mark.
            shutdown: the interface will be shutdown if receiving-rate is higher than the high water mark and the interface will NOT be open when the receiving-rate drops below the low water mark. To open the interface, use undo shutdown command."
        DEFVAL { none }
        ::= { hwXQoSStormControlEntry 6 }


    hwXQoSStormControlInterval OBJECT-TYPE
        SYNTAX Integer32 (1..180)
        MAX-ACCESS read-write
        STATUS current
        DESCRIPTION
            "The interval that the broadcast storm or multicast storm will be checked. Unit: second."
        DEFVAL { 3 }
        ::= { hwXQoSStormControlEntry 7 }

    hwXQoSStormControlTrapEnable OBJECT-TYPE
        SYNTAX EnabledStatus
        MAX-ACCESS read-write
        STATUS current
        DESCRIPTION
            "Enable or disable trap.
            enable(1): report trap when interface status changes.
            disable(2): do not report trap when interface status changes. "
        ::= { hwXQoSStormControlEntry 8 }

    hwXQoSStormControlLogEnable OBJECT-TYPE
        SYNTAX EnabledStatus
        MAX-ACCESS read-write
        STATUS current
        DESCRIPTION
            "Enable or disable log.
            enable(1): record log when interface status changes.
            disable(2): do not record log when interface status changes. "
        ::= { hwXQoSStormControlEntry 9 }


    hwXQoSStormControlStatus OBJECT-TYPE
        SYNTAX INTEGER
            {
            normal(1),
            broadcastBlocked(2),
            multicastBlocked(3),
            bothBlocked(4),
            shutdown(5),
            unicastBlocked(6),
            allBlocked(7),
            bcmcBlocked(8),
            bcucBlocked(9),
            ucmcBlocked(10)
            }
        MAX-ACCESS read-only
        STATUS current
        DESCRIPTION
            "The status of the interface.
            normal: no storm-control action is taken.
            broadcastBlocked: broadcast packets is blocked.
            multicastBlocked: multicast packets is blocked.
            bothBlocked: both the broadcast and multicast packets are blocked.
            shutdown: the interface is shutdown.
            unicastBlocked: unicast packets is blocked.
            allBlocked: broadcast multicast unicast packets is blocked.
            bcmcBlocked: both the broadcast and multicast packets are blocked.
            bcucBlocked: both the broadcast and unicast packets are blocked.
            ucmcBlocked: both the unicast and multicast packets are blocked."
        ::= { hwXQoSStormControlEntry 10 }

    hwXQoSStormControlUnicastMinRate OBJECT-TYPE
        SYNTAX Integer32 (0..14881000)
        MAX-ACCESS read-write
        STATUS current
        DESCRIPTION
            "The low water mark of unicast packets rate. Unit: pps (packets per second).
            zero : storm-control function is not enable for unicast packets."
        DEFVAL { 0 }
        ::= { hwXQoSStormControlEntry 11 }

    hwXQoSStormControlUnicastMaxRate OBJECT-TYPE
        SYNTAX Integer32 (0..14881000)
        MAX-ACCESS read-write
        STATUS current
        DESCRIPTION
            "The high water mark of unicast packets rate. Unit: pps (packets per second).
            zero : storm-control function is not enable for unicast packets."
        DEFVAL { 0 }
        ::= { hwXQoSStormControlEntry 12 }

    hwXQoSStormControlBcMode OBJECT-TYPE
        SYNTAX INTEGER {
            pps(0),
            kbps(1),
            percent(2),
            none(3)
            }
        MAX-ACCESS read-write
        STATUS current
        DESCRIPTION
            "The mode of broadcast packets.
            pps : (packets per second).
            kbps : (kbit per second).
            percent : (%).
            none: initialization."
        DEFVAL { none }
        ::= { hwXQoSStormControlEntry 13 }

    hwXQoSStormControlMcMode OBJECT-TYPE
        SYNTAX INTEGER {
            pps(0),
            kbps(1),
            percent(2),
            none(3)
            }
        MAX-ACCESS read-write
        STATUS current
        DESCRIPTION
            "The mode of multicast packets.
            pps : (packets per second).
            kbps : (kbit per second).
            percent : (%).
            none: initialization."
        DEFVAL { none }
        ::= { hwXQoSStormControlEntry 14 }

    hwXQoSStormControlUcMode OBJECT-TYPE
        SYNTAX INTEGER {
            pps(0),
            kbps(1),
            percent(2),
            none(3)
            }
        MAX-ACCESS read-write
        STATUS current
        DESCRIPTION
            "The mode of unicast packets.
            pps : (packets per second).
            kbps : (kbit per second).
            percent : (%).
            none: initialization."
        DEFVAL { none }
        ::= { hwXQoSStormControlEntry 15 }

    hwXQoSStormControlIfName OBJECT-TYPE
        SYNTAX OCTET STRING
        MAX-ACCESS accessible-for-notify
        STATUS current
        DESCRIPTION
            "The interface name."
        ::= { hwXQoSStormControlEntry 16 }

    hwXQoSStormControlUnknownUnicastMinRate OBJECT-TYPE
        SYNTAX Integer32 (0..14881000)
        MAX-ACCESS read-write
        STATUS current
        DESCRIPTION
            "The low water mark of unknown unicast packets rate. Unit: pps (packets per second).
            zero : storm-control function is not enable for unknown unicast packets."
        DEFVAL { 0 }
        ::= { hwXQoSStormControlEntry 17 }

    hwXQoSStormControlUnknownUnicastMaxRate OBJECT-TYPE
        SYNTAX Integer32 (0..14881000)
        MAX-ACCESS read-write
        STATUS current
        DESCRIPTION
            "The high water mark of unknown unicast packets rate. Unit: pps (packets per second).
            zero : storm-control function is not enable for unknown unicast packets."
        DEFVAL { 0 }
        ::= { hwXQoSStormControlEntry 18 }

    hwXQoSStormControlUnknownUcMode OBJECT-TYPE
        SYNTAX INTEGER {
            pps(0),
            kbps(1),
            percent(2),
            none(3)
            }
        MAX-ACCESS read-write
        STATUS current
        DESCRIPTION
            "The mode of unknown unicast packets.
            pps : (packets per second).
            kbps : (kbit per second).
            percent : (%).
            none: initialization."
        DEFVAL { none }
        ::= { hwXQoSStormControlEntry 19}

    hwXQoSStormControlActionName OBJECT-TYPE
        SYNTAX OCTET STRING
        MAX-ACCESS read-write
        STATUS current
        DESCRIPTION
            "Storm control action."
        ::= { hwXQoSStormControlEntry 20 }

    hwXQoSStormControlType OBJECT-TYPE
        SYNTAX OCTET STRING
        MAX-ACCESS read-write
        STATUS current
        DESCRIPTION
            "Storm control type."
        ::= { hwXQoSStormControlEntry 21 }

    hwXQoSStormControlThreshold OBJECT-TYPE
        SYNTAX Integer32 (0..14881000)
        MAX-ACCESS read-write
        STATUS current
        DESCRIPTION
            "The threshold of storm control. Unit: pps or kbps."
        DEFVAL { 0 }
        ::= { hwXQoSStormControlEntry 22 }

    hwXQoSStormControlMode OBJECT-TYPE
        SYNTAX OCTET STRING
        MAX-ACCESS read-write
        STATUS current
        DESCRIPTION
            "Storm control mode."
        ::= { hwXQoSStormControlEntry 23 }

    hwXQoSStormControlBroadcastRate OBJECT-TYPE
        SYNTAX Integer32
        MAX-ACCESS read-only
        STATUS current
        DESCRIPTION
            "The broadcast packets rate. Unit: pps (packets per second)."
        ::= { hwXQoSStormControlEntry 24 }

    hwXQoSStormControlMulticastRate OBJECT-TYPE
        SYNTAX Integer32
        MAX-ACCESS read-only
        STATUS current
        DESCRIPTION
            "The multicast packets rate. Unit: pps (packets per second)."
        ::= { hwXQoSStormControlEntry 25 }

    hwXQoSStormControlUnicastRate OBJECT-TYPE
        SYNTAX Integer32
        MAX-ACCESS read-only
        STATUS current
        DESCRIPTION
            "The unicast packets rate. Unit: pps (packets per second)."
        ::= { hwXQoSStormControlEntry 26 }

    hwXQoSTrafficSuppressionTable OBJECT-TYPE
        SYNTAX SEQUENCE OF HwXQoSTrafficSuppressionEntry
        MAX-ACCESS not-accessible
        STATUS current
        DESCRIPTION
            "A table about traffic suppression configuration information."
        ::= { hwXQoSStormControlObjects 2 }


    hwXQoSTrafficSuppressionEntry OBJECT-TYPE
        SYNTAX HwXQoSTrafficSuppressionEntry
        MAX-ACCESS not-accessible
        STATUS current
        DESCRIPTION
            "Traffic suppression configuration information entry."
        INDEX { hwXQoSTrafficSuppIfIndex }
        ::= { hwXQoSTrafficSuppressionTable 1 }


    HwXQoSTrafficSuppressionEntry ::=
        SEQUENCE {
            hwXQoSTrafficSuppIfIndex
                InterfaceIndex,
            hwXQoSTrafficSuppIfName
                OCTET STRING,
            hwXQoSTrafficSuppBroadDropPkts
                Counter64,
            hwXQoSTrafficSuppMultiDropPkts
                Counter64,
            hwXQoSTrafficSuppUniDropPkts
                Counter64,
            hwXQoSTrafficSuppKnownMultiDropPkts
                Counter64,
            hwXQoSTrafficSuppKnownUniDropPkts
                Counter64
            }

    hwXQoSTrafficSuppIfIndex OBJECT-TYPE
        SYNTAX InterfaceIndex
        MAX-ACCESS accessible-for-notify
        STATUS current
        DESCRIPTION
            "The interface index, equal to ifIndex."
        ::= { hwXQoSTrafficSuppressionEntry 1 }

    hwXQoSTrafficSuppIfName OBJECT-TYPE
        SYNTAX OCTET STRING
        MAX-ACCESS accessible-for-notify
        STATUS current
        DESCRIPTION
            "The interface name."
        ::= { hwXQoSTrafficSuppressionEntry 2 }

    hwXQoSTrafficSuppBroadDropPkts OBJECT-TYPE
        SYNTAX Counter64
        MAX-ACCESS accessible-for-notify
        STATUS current
        DESCRIPTION
            "The number of packets dropped by broadcast traffic suppression."
        ::= { hwXQoSTrafficSuppressionEntry 3 }

    hwXQoSTrafficSuppMultiDropPkts OBJECT-TYPE
        SYNTAX Counter64
        MAX-ACCESS accessible-for-notify
        STATUS current
        DESCRIPTION
            "The number of packets dropped by unknown multicast traffic suppression."
        ::= { hwXQoSTrafficSuppressionEntry 4 }

    hwXQoSTrafficSuppUniDropPkts OBJECT-TYPE
        SYNTAX Counter64
        MAX-ACCESS accessible-for-notify
        STATUS current
        DESCRIPTION
            "The number of packets dropped by unknown unicast traffic suppression."
        ::= { hwXQoSTrafficSuppressionEntry 5 }

    hwXQoSTrafficSuppKnownMultiDropPkts OBJECT-TYPE
        SYNTAX Counter64
        MAX-ACCESS accessible-for-notify
        STATUS current
        DESCRIPTION
            "The number of packets dropped by known multicast traffic suppression."
        ::= { hwXQoSTrafficSuppressionEntry 6 }

    hwXQoSTrafficSuppKnownUniDropPkts OBJECT-TYPE
        SYNTAX Counter64
        MAX-ACCESS accessible-for-notify
        STATUS current
        DESCRIPTION
            "The number of packets dropped by known unicast traffic suppression."
        ::= { hwXQoSTrafficSuppressionEntry 7 }

    hwXQoSStormControlNotification OBJECT IDENTIFIER ::= { hwXQoSObjects 14 }


    hwXQoSStormControlTrap NOTIFICATION-TYPE
        OBJECTS { hwXQoSStormControlBroadcastMinRate, hwXQoSStormControlBroadcastMaxRate, hwXQoSStormControlMulticastMinRate, hwXQoSStormControlMulticastMaxRate,
            hwXQoSStormControlAction, hwXQoSStormControlInterval, hwXQoSStormControlStatus, hwXQoSStormControlUnicastMinRate, hwXQoSStormControlUnicastMaxRate, hwXQoSStormControlBcMode ,hwXQoSStormControlMcMode,
            hwXQoSStormControlUcMode,  hwXQoSStormControlUnknownUcMode,  hwXQoSStormControlUnknownUnicastMinRate, hwXQoSStormControlUnknownUnicastMaxRate}
        STATUS current
        DESCRIPTION
            "The SNMP trap is generated when the status of interface is changed for storm-control.
            hwXQoSStormControlBroadcastMinRate: The low water mark of broadcast packets rate.
            hwXQoSStormControlBroadcastMaxRate: The high water mark of broadcast packets rate.
            hwXQoSStormControlMulticastMinRate: The low water mark of multicast packets rate.
            hwXQoSStormControlMulticastMaxRate: The high water mark of multicast packets rate.
            hwXQoSStormControlAction: The storm-control action.
            hwXQoSStormControlInterval: The interval that the broadcast storm or multicast storm will be checked.
            hwXQoSStormControlStatus: The status of the interface.
            hwXQoSStormControlUnicastMinRate: The low water mark of unicast packets rate.
            hwXQoSStormControlUniicastMaxRate: The high water mark of unicast packets rate.
            hwXQoSStormControlBcMode: The mode of Broadcast packets.
            hwXQoSStormControlMcMode: The mode of multicast packets.
            hwXQoSStormControlUcMode: The mode of unicast packets.
            hwXQoSStormControlUnknownUcMode: The mode of unknown unicast packets.
            hwXQoSStormControlUnknownUnicastMinRate: The low water mark of unknown unicast packets rate.
            hwXQoSStormControlUnknownUnicastMaxRate: The high water mark of unknown unicast packets rate."
        ::= { hwXQoSStormControlNotification 1 }


    hwXQoSStormControlTrapExt NOTIFICATION-TYPE
        OBJECTS { hwXQoSStormControlIfIndex, hwXQoSStormControlIfName, hwXQoSStormControlBroadcastMinRate, hwXQoSStormControlBroadcastMaxRate, hwXQoSStormControlMulticastMinRate,
hwXQoSStormControlMulticastMaxRate, hwXQoSStormControlAction, hwXQoSStormControlInterval, hwXQoSStormControlStatus, hwXQoSStormControlUnicastMinRate,
hwXQoSStormControlUnicastMaxRate, hwXQoSStormControlBcMode, hwXQoSStormControlMcMode, hwXQoSStormControlUcMode, hwXQoSStormControlBroadcastRate, hwXQoSStormControlMulticastRate, hwXQoSStormControlUnicastRate }
        STATUS current
        DESCRIPTION
            "The SNMP trap is generated when the status of interface is changed for storm-control.
            hwXQoSStormControlIfIndex: The interface index, equal to ifIndex.
            hwXQoSStormControlIfName: The interface name.
            hwXQoSStormControlBroadcastMinRate: The low water mark of broadcast packets rate.
            hwXQoSStormControlBroadcastMaxRate: The high water mark of broadcast packets rate.
            hwXQoSStormControlMulticastMinRate: The low water mark of multicast packets rate.
            hwXQoSStormControlMulticastMaxRate: The high water mark of multicast packets rate.
            hwXQoSStormControlAction: The storm-control action.
            hwXQoSStormControlInterval: The interval that the broadcast storm or multicast storm will be checked.
            hwXQoSStormControlStatus: The status of the interface.
            hwXQoSStormControlUnicastMinRate: The low water mark of unicast packets rate.
            hwXQoSStormControlUniicastMaxRate: The high water mark of unicast packets rate.
            hwXQoSStormControlBcMode: The mode of Broadcast packets.
            hwXQoSStormControlMcMode: The mode of multicast packets.
            hwXQoSStormControlUcMode: The mode of unicast packets.
            hwXQoSStormControlBroadcastRate: The broadcast packets rate.
            hwXQoSStormControlMulticastRate: The multicast packets rate.
            hwXQoSStormControlUnicastRate: The unicast packets rate."
        ::= { hwXQoSStormControlNotification 2 }

    hwXQoSTrafficSuppressionTrap NOTIFICATION-TYPE
        OBJECTS { hwXQoSTrafficSuppIfIndex, hwXQoSTrafficSuppIfName, hwXQoSTrafficSuppBroadDropPkts, hwXQoSTrafficSuppMultiDropPkts,
            hwXQoSTrafficSuppUniDropPkts, hwXQoSTrafficSuppKnownMultiDropPkts, hwXQoSTrafficSuppKnownUniDropPkts}
        STATUS current
        DESCRIPTION
            "The SNMP trap is generated when incoming packet loss occurs due to traffic suppression.
            hwXQoSTrafficSuppIfIndex: The interface index, equal to ifIndex.
            hwXQoSTrafficSuppIfName: The interface name.
            hwXQoSTrafficSuppBroadDropPkts: The number of packets dropped by broadcast traffic suppression.
            hwXQoSTrafficSuppMultiDropPkts: The number of packets dropped by unknown multicast traffic suppression.
            hwXQoSTrafficSuppUniDropPkts: The number of packets dropped by unknown unicast traffic suppression.
            hwXQoSTrafficSuppKnownMultiDropPkts: The number of packets dropped by known multicast traffic suppression.
            hwXQoSTrafficSuppKnownUniDropPkts: The number of packets dropped by known unicast traffic suppression."
        ::= { hwXQoSStormControlNotification 3 }

    hwXQoSQueueStatisticsObjects OBJECT IDENTIFIER ::= { hwXQoSObjects 15 }

    hwXQoSQueueStatisticsTable OBJECT-TYPE
            SYNTAX SEQUENCE OF HwXQoSQueueStatisticsEntry
            MAX-ACCESS not-accessible
            STATUS current
            DESCRIPTION
                    "A Table about queue statistics."
            ::= { hwXQoSQueueStatisticsObjects 1 }

    hwXQoSQueueStatisticsEntry OBJECT-TYPE
        SYNTAX HwXQoSQueueStatisticsEntry
        MAX-ACCESS not-accessible
        STATUS current
        DESCRIPTION
                "The entry of queue statistics infomation."
        INDEX { hwXQoSQueueStatisticsIngressIfIndex, hwXQoSQueueStatisticsEgressIfIndex, hwXQoSQueueStatisticsQueueIndex }
        ::= { hwXQoSQueueStatisticsTable 1 }

    HwXQoSQueueStatisticsEntry ::=
        SEQUENCE {
            hwXQoSQueueStatisticsIngressIfIndex
                    InterfaceIndex,
            hwXQoSQueueStatisticsEgressIfIndex
                    InterfaceIndex,
            hwXQoSQueueStatisticsQueueIndex
                    INTEGER,
            hwXQoSQueueStatisticsPassedPacketsCount
                    Counter64,
            hwXQosQueueStatisticsReset
                    INTEGER,
            hwXQoSQueueStatisticsRowStatus
                    RowStatus
            }

    hwXQoSQueueStatisticsIngressIfIndex OBJECT-TYPE
        SYNTAX InterfaceIndex
        MAX-ACCESS not-accessible
        STATUS current
        DESCRIPTION
            "The ingress interface index.
            2147483647: invalid interface index, the statistics will be the count of packets of the egress interface and queue.
            The ingress interface index and the egress interface index can not be 2147483647 at the same time."
        ::= { hwXQoSQueueStatisticsEntry 1 }

    hwXQoSQueueStatisticsEgressIfIndex OBJECT-TYPE
        SYNTAX InterfaceIndex
        MAX-ACCESS not-accessible
        STATUS current
        DESCRIPTION
            "The egress interface index.
            2147483647: invalid interface index, the statistics will be the count of packets of the ingress interface and queue.
            The ingress interface index and the egress interface index can not be 2147483647 at the same time. "
        ::= { hwXQoSQueueStatisticsEntry 2 }

    hwXQoSQueueStatisticsQueueIndex OBJECT-TYPE
        SYNTAX INTEGER
            {
            be(1),
            af1(2),
            af2(3),
            af3(4),
            af4(5),
            ef(6),
            cs6(7),
            cs7(8)
            }
        MAX-ACCESS not-accessible
        STATUS current
        DESCRIPTION
            "The queue index."
        ::= { hwXQoSQueueStatisticsEntry 3 }

    hwXQoSQueueStatisticsPassedPacketsCount OBJECT-TYPE
        SYNTAX Counter64
        MAX-ACCESS read-only
        STATUS current
        DESCRIPTION
            "The passed packets count.
            If the ingress interface index is 2147483647, this node will be the count of passed packets of the specified queue of the ingress interface.
            If the egress interface index is 2147483647, this node will be the count of passed packets of the specified queue of the ingress interface.
            If none of the ingress and egress interface is 2147483647, this node will be the count of passed packets which is from the ingress interface to
            the egress interface at the specified queue.
            The ingress interface index and the egress interface index can not be 2147483647 at the same time ."
        ::= { hwXQoSQueueStatisticsEntry 4 }

    hwXQosQueueStatisticsReset OBJECT-TYPE
        SYNTAX INTEGER
            {
            reset(1)
            }
        MAX-ACCESS read-create
        STATUS current
        DESCRIPTION
            "Set this node to reset the counter.
                Reset(1) will be returned if this node is read."
        ::= { hwXQoSQueueStatisticsEntry 5 }

    hwXQoSQueueStatisticsRowStatus OBJECT-TYPE
            SYNTAX RowStatus
            MAX-ACCESS read-create
            STATUS current
            DESCRIPTION
                    "RowStatus. Three actions are used:
                    active,createandgo, destroy"
            ::= { hwXQoSQueueStatisticsEntry 6 }


    hwXQoSPortStatisticsDropObjects OBJECT IDENTIFIER ::= { hwXQoSObjects 16 }


    hwXQoSPortStatisticsDropTable OBJECT-TYPE
            SYNTAX SEQUENCE OF HwXQoSPortStatisticsDropEntry
            MAX-ACCESS not-accessible
            STATUS current
            DESCRIPTION
                    "A table about drop packets statistics of port."
            ::= { hwXQoSPortStatisticsDropObjects 1 }


    hwXQoSPortStatisticsDropEntry OBJECT-TYPE
        SYNTAX HwXQoSPortStatisticsDropEntry
        MAX-ACCESS not-accessible
        STATUS current
        DESCRIPTION
            "The entry about drop packets statistics of port."
        INDEX { hwXQoSPortStatisticsDropIfIndex}
        ::= { hwXQoSPortStatisticsDropTable 1 }


    HwXQoSPortStatisticsDropEntry ::=
        SEQUENCE {
            hwXQoSPortStatisticsDropIfIndex
                InterfaceIndex,
            hwXQoSPortStatisticsDropPacketsCount
                Counter64,
            hwXQosPortStatisticsDropReset
                INTEGER,
            hwXQosPortStatisticsDropResetTime
                TimeTicks
            }

    hwXQoSPortStatisticsDropIfIndex OBJECT-TYPE
        SYNTAX InterfaceIndex
        MAX-ACCESS not-accessible
        STATUS current
        DESCRIPTION
            "The interface index."
        ::= { hwXQoSPortStatisticsDropEntry 1 }


    hwXQoSPortStatisticsDropPacketsCount OBJECT-TYPE
        SYNTAX Counter64
        MAX-ACCESS read-only
        STATUS current
        DESCRIPTION
            "The dropped packets count of the port."
        ::= { hwXQoSPortStatisticsDropEntry 2 }

    hwXQosPortStatisticsDropReset OBJECT-TYPE
        SYNTAX INTEGER
            {
            reset(1)
            }
        MAX-ACCESS read-write
        STATUS current
        DESCRIPTION
            "Set this node to reset the counter.
            Reset(1) will be returned if this node is read."
        ::= { hwXQoSPortStatisticsDropEntry 3 }

    hwXQosPortStatisticsDropResetTime OBJECT-TYPE
        SYNTAX TimeTicks
        MAX-ACCESS read-only
        STATUS current
        DESCRIPTION
            "The value of sysUpTime on the most recent occasion at
                which one of this interface's counters
                suffered a discontinuity. If no such discontinuities have
                occurred since the last re-initialization of the local
                management subsystem, then this object contains a zero
                value."
        ::= { hwXQoSPortStatisticsDropEntry 4 }

    hwXQoSQueueStatisticsDropObjects OBJECT IDENTIFIER ::= { hwXQoSObjects 17 }

    hwXQoSQueueStatisticsDropTable OBJECT-TYPE
        SYNTAX SEQUENCE OF HwXQoSQueueStatisticsDropEntry
        MAX-ACCESS not-accessible
        STATUS current
        DESCRIPTION
            "A table about drop packets statistics of queue."
        ::= { hwXQoSQueueStatisticsDropObjects 1 }

    hwXQoSQueueStatisticsDropEntry OBJECT-TYPE
        SYNTAX HwXQoSQueueStatisticsDropEntry
        MAX-ACCESS not-accessible
        STATUS current
        DESCRIPTION
            "The entry about drop packets statistics of queue."
        INDEX { hwXQoSQueueStatisticsDropIfIndex,hwXQoSQueueStatisticsDropQueueIndex }
        ::= { hwXQoSQueueStatisticsDropTable 1 }


    HwXQoSQueueStatisticsDropEntry ::=
        SEQUENCE {
            hwXQoSQueueStatisticsDropIfIndex
                    InterfaceIndex,
            hwXQoSQueueStatisticsDropQueueIndex
                    INTEGER,
            hwXQoSQueueStatisticsDropPacketsCount
                    Counter64,
            hwXQosQueueStatisticsDropReset
                    INTEGER,
            hwXQosQueueStatisticsDropResetTime
                    TimeTicks
            }

    hwXQoSQueueStatisticsDropIfIndex OBJECT-TYPE
        SYNTAX InterfaceIndex
        MAX-ACCESS not-accessible
        STATUS current
        DESCRIPTION
            "The interface index."
        ::= { hwXQoSQueueStatisticsDropEntry 1 }

    hwXQoSQueueStatisticsDropQueueIndex OBJECT-TYPE
        SYNTAX INTEGER
            {
            be(1),
            af1(2),
            af2(3),
            af3(4),
            af4(5),
            ef(6),
            cs6(7),
            cs7(8)
            }
        MAX-ACCESS not-accessible
        STATUS current
        DESCRIPTION
            "The queue index."
        ::= { hwXQoSQueueStatisticsDropEntry 2 }

    hwXQoSQueueStatisticsDropPacketsCount OBJECT-TYPE
        SYNTAX Counter64
        MAX-ACCESS read-only
        STATUS current
        DESCRIPTION
            "The dropped packets count of the queue."
        ::= { hwXQoSQueueStatisticsDropEntry 3 }

    hwXQosQueueStatisticsDropReset OBJECT-TYPE
        SYNTAX INTEGER
            {
            reset(1)
            }
        MAX-ACCESS read-write
        STATUS current
        DESCRIPTION
            "Set this node to reset the counter.
                Reset(1) will be returned if this node is read."
        ::= { hwXQoSQueueStatisticsDropEntry 4 }

    hwXQosQueueStatisticsDropResetTime OBJECT-TYPE
        SYNTAX TimeTicks
        MAX-ACCESS read-only
        STATUS current
        DESCRIPTION
            "The value of sysUpTime on the most recent occasion at
                which  one of this queue's counters
                suffered a discontinuity. If no such discontinuities have
                occurred since the last re-initialization of the local
                management subsystem, then this object contains a zero
                value."
        ::= { hwXQoSQueueStatisticsDropEntry 5 }

  --rulefail

    hwXQoSRuleFailObjects OBJECT IDENTIFIER ::= { hwXQoSObjects 18 }

    hwXQoSRuleFailTable OBJECT-TYPE
        SYNTAX SEQUENCE OF HwXQoSRuleFailEntry
        MAX-ACCESS not-accessible
        STATUS current
        DESCRIPTION
            "hwXQoSRuleFailTable"
        ::= { hwXQoSRuleFailObjects 1 }

    hwXQoSRuleFailEntry OBJECT-TYPE
        SYNTAX HwXQoSRuleFailEntry
        MAX-ACCESS not-accessible
        STATUS current
        DESCRIPTION
            "hwXQoSRuleFailEntry"
        INDEX { hwXQoSRuleFailInfo }
        ::= { hwXQoSRuleFailTable 1 }

    HwXQoSRuleFailEntry ::=
        SEQUENCE {
            hwXQoSRuleFailInfo
                OCTET STRING
                }

    hwXQoSRuleFailInfo OBJECT-TYPE
        SYNTAX OCTET STRING (SIZE (1..32))
        MAX-ACCESS read-only
        STATUS current
        DESCRIPTION
            "ACL Rule Exhaustion Information"
        ::= { hwXQoSRuleFailEntry 1 }

-- profile alarm
    hwXQoSProfileObjects OBJECT IDENTIFIER ::= { hwXQoSObjects 19 }

    hwXQoSProfileTable OBJECT-TYPE
        SYNTAX SEQUENCE OF HwXQoSProfileEntry
        MAX-ACCESS not-accessible
        STATUS current
        DESCRIPTION
            "A table of the qos-profile"
        ::= { hwXQoSProfileObjects 1 }

    hwXQoSProfileEntry OBJECT-TYPE
        SYNTAX HwXQoSProfileEntry
        MAX-ACCESS not-accessible
        STATUS current
        DESCRIPTION
            "A table of the redirect next hop information"
        INDEX { hwXQoSProfileName }
        ::= { hwXQoSProfileTable 1 }

    HwXQoSProfileEntry ::=
        SEQUENCE {
            hwXQoSProfileName
                OCTET STRING
            }

    hwXQoSProfileName OBJECT-TYPE
        SYNTAX OCTET STRING (SIZE (1..63))
        MAX-ACCESS read-only
        STATUS current
        DESCRIPTION
            "Qos-profile name."
        ::= { hwXQoSProfileEntry 1 }

        --port queue alarm
        hwXQoSPortQueueAlarmObjects OBJECT IDENTIFIER ::= { hwXQoSObjects 20 }

    hwXQoSPortQueueAlarmTable OBJECT-TYPE
        SYNTAX SEQUENCE OF HwXQoSPortQueueAlarmEntry
        MAX-ACCESS not-accessible
        STATUS current
        DESCRIPTION
            "hwXQoSPortQueueAlarmTable"
        ::= { hwXQoSPortQueueAlarmObjects 1 }

    hwXQoSPortQueueAlarmEntry OBJECT-TYPE
        SYNTAX HwXQoSPortQueueAlarmEntry
        MAX-ACCESS not-accessible
        STATUS current
        DESCRIPTION
            "hwXQoSPortQueueAlarmEntry"
        INDEX { hwXQoSPortQueueAlarmIfIndex }
        ::= { hwXQoSPortQueueAlarmTable 1 }

    HwXQoSPortQueueAlarmEntry ::=
        SEQUENCE {
            hwXQoSPortQueueAlarmIfIndex
                InterfaceIndex,
            hwXQoSPortQueueAlarmQueue
                OCTET STRING,
            hwXQoSPortQueueAlarmTrunkIndex
                InterfaceIndex
                }

    hwXQoSPortQueueAlarmIfIndex OBJECT-TYPE
            SYNTAX InterfaceIndex
            MAX-ACCESS read-only
            STATUS current
            DESCRIPTION
                    "The interface index."
            ::= { hwXQoSPortQueueAlarmEntry 1 }

    hwXQoSPortQueueAlarmQueue OBJECT-TYPE
        SYNTAX OCTET STRING (SIZE (1..4))
        MAX-ACCESS read-write
        STATUS current
        DESCRIPTION
            "hwXQoSPortQueueAlarmQueue."
        ::= { hwXQoSPortQueueAlarmEntry 2 }

    hwXQoSPortQueueAlarmTrunkIndex OBJECT-TYPE
        SYNTAX InterfaceIndex
        MAX-ACCESS read-write
        STATUS current
        DESCRIPTION
                "The trunk interface index."
        ::= { hwXQoSPortQueueAlarmEntry 3 }

    hwXQoSPortQueueAlarmExTable OBJECT-TYPE
        SYNTAX SEQUENCE OF HwXQoSPortQueueAlarmExEntry
        MAX-ACCESS not-accessible
        STATUS current
        DESCRIPTION
            "This table is used to display the alarm information about a port queue."
        ::= { hwXQoSPortQueueAlarmObjects 2 }

    hwXQoSPortQueueAlarmExEntry OBJECT-TYPE
        SYNTAX HwXQoSPortQueueAlarmExEntry
        MAX-ACCESS not-accessible
        STATUS current
        DESCRIPTION
            "hwXQoSPortQueueAlarmExEntry"
        INDEX { hwXQoSPortQueueAlarmExIfIndex,
                hwXQoSPortQueueAlarmExQueue}
        ::= { hwXQoSPortQueueAlarmExTable 1 }

    HwXQoSPortQueueAlarmExEntry ::=
        SEQUENCE {
            hwXQoSPortQueueAlarmExIfIndex
                InterfaceIndex,
            hwXQoSPortQueueAlarmExQueue
                INTEGER,
            hwXQoSPortQueueAlarmExBuffer
                Integer32
                }

    hwXQoSPortQueueAlarmExIfIndex OBJECT-TYPE
            SYNTAX InterfaceIndex
            MAX-ACCESS read-only
            STATUS current
            DESCRIPTION
                "This object indicates the index of the port queue alarm interface."
            ::= { hwXQoSPortQueueAlarmExEntry 1 }

    hwXQoSPortQueueAlarmExQueue OBJECT-TYPE
        SYNTAX INTEGER
        {
            be(1),
            af1(2),
            af2(3),
            af3(4),
            af4(5),
            ef(6),
            cs6(7),
            cs7(8)
        }
        MAX-ACCESS read-only
        STATUS current
        DESCRIPTION
            " This object indicates the service class of the port queue.
                Value range:
                1 be
                2 af1
                3 af2
                4 af3
                5 af4
                6 ef
                7 cs6
                8 cs7.
            "
        ::= { hwXQoSPortQueueAlarmExEntry 2 }

    hwXQoSPortQueueAlarmExBuffer OBJECT-TYPE
        SYNTAX Integer32
        MAX-ACCESS read-only
        STATUS current
        DESCRIPTION
            "This object indicates the alarm buffer information about the port queue."
        ::= { hwXQoSPortQueueAlarmExEntry 3 }


    hwXQOSQueueBufferOverrunAlarmTable OBJECT-TYPE
        SYNTAX SEQUENCE OF HwXQOSQueueBufferOverrunAlarmEntry
        MAX-ACCESS not-accessible
        STATUS current
        DESCRIPTION
            "hwXQOSQueueBufferOverrunAlarmTable"
        ::= { hwXQoSPortQueueAlarmObjects 3 }

    hwXQOSQueueBufferOverrunAlarmEntry OBJECT-TYPE
        SYNTAX HwXQOSQueueBufferOverrunAlarmEntry
        MAX-ACCESS not-accessible
        STATUS current
        DESCRIPTION
            "hwXQOSQueueBufferOverrunAlarmEntry"
        INDEX { hwXQOSQueueBufferAlarmChassisID, hwXQOSQueueBufferAlarmSlotID, hwXQOSQueueBufferAlarmIfIndex, hwXQOSQueueBufferAlarmQueueID}
        ::= { hwXQOSQueueBufferOverrunAlarmTable 1 }

    HwXQOSQueueBufferOverrunAlarmEntry ::=
        SEQUENCE {
            hwXQOSQueueBufferAlarmChassisID
                Integer32,
            hwXQOSQueueBufferAlarmSlotID
                Integer32,
            hwXQOSQueueBufferAlarmIfIndex
                InterfaceIndex,
            hwXQOSQueueBufferAlarmQueueID
                Integer32,
            hwXQOSQueueBufferAlarmUsedCell
                Integer32,
            hwXQOSQueueBufferAlarmUsedLength
                Integer32,
            hwXQOSQueueBufferAlarmThreshold
                Integer32,
            hwXQOSQueueBufferAlarmDiscard
                Counter64
                }

    hwXQOSQueueBufferAlarmChassisID OBJECT-TYPE
        SYNTAX Integer32
        MAX-ACCESS read-only
        STATUS current
        DESCRIPTION
            "The information of the chassis."
        ::= { hwXQOSQueueBufferOverrunAlarmEntry 1 }

    hwXQOSQueueBufferAlarmSlotID OBJECT-TYPE
        SYNTAX Integer32
        MAX-ACCESS read-only
        STATUS current
        DESCRIPTION
            "The information of the slot."
        ::= { hwXQOSQueueBufferOverrunAlarmEntry 2 }

    hwXQOSQueueBufferAlarmIfIndex OBJECT-TYPE
        SYNTAX InterfaceIndex
        MAX-ACCESS read-only
        STATUS current
        DESCRIPTION
            "The index of physical interface."
        ::= { hwXQOSQueueBufferOverrunAlarmEntry 3 }

    hwXQOSQueueBufferAlarmQueueID OBJECT-TYPE
        SYNTAX Integer32
        MAX-ACCESS read-only
        STATUS current
        DESCRIPTION
            "The index of the congested queue."
        ::= { hwXQOSQueueBufferOverrunAlarmEntry 4 }

    hwXQOSQueueBufferAlarmUsedCell OBJECT-TYPE
        SYNTAX Integer32
        MAX-ACCESS read-only
        STATUS current
        DESCRIPTION
            "The used buffer cell of queue when congestion was detected."
        ::= { hwXQOSQueueBufferOverrunAlarmEntry 5 }

    hwXQOSQueueBufferAlarmUsedLength OBJECT-TYPE
        SYNTAX Integer32
        MAX-ACCESS read-only
        STATUS current
        DESCRIPTION
            "The used buffer length(uint:KBytes) of queue when congestion was detected. "
        ::= { hwXQOSQueueBufferOverrunAlarmEntry 6 }

    hwXQOSQueueBufferAlarmThreshold OBJECT-TYPE
        SYNTAX Integer32
        MAX-ACCESS read-only
        STATUS current
        DESCRIPTION
            "The current buffer overrun threshold. "
        ::= { hwXQOSQueueBufferOverrunAlarmEntry 7 }

    hwXQOSQueueBufferAlarmDiscard OBJECT-TYPE
        SYNTAX Counter64
        MAX-ACCESS read-only
        STATUS current
        DESCRIPTION
            "The current Discard. "
        ::= { hwXQOSQueueBufferOverrunAlarmEntry 8 }

    hwXQoSIfLrDiscardAlarmTable OBJECT-TYPE
        SYNTAX SEQUENCE OF HwXQoSIfLrDiscardAlarmEntry
        MAX-ACCESS not-accessible
        STATUS current
        DESCRIPTION
            "hwXQoSIfLrDiscardAlarmTable"
        ::= { hwXQoSPortQueueAlarmObjects 4 }

    hwXQoSIfLrDiscardAlarmEntry OBJECT-TYPE
        SYNTAX HwXQoSIfLrDiscardAlarmEntry
        MAX-ACCESS not-accessible
        STATUS current
        DESCRIPTION
            "hwXQoSIfLrDiscardAlarmEntry"
        INDEX { hwXQoSIfLrDiscardAlarmIfIndex}
        ::= { hwXQoSIfLrDiscardAlarmTable 1 }

    HwXQoSIfLrDiscardAlarmEntry ::=
        SEQUENCE {
                hwXQoSIfLrDiscardAlarmIfIndex
                    InterfaceIndex,
                hwXQoSIfLrDiscardAlarmIfName
                    OCTET STRING,
                hwXQoSIfLrDiscardAlarmCir
                    Integer32,
                hwXQoSIfLrDiscardAlarmTrapThreshold
                    Integer32,
                hwXQoSIfLrDiscardAlarmPassPacketRate
                    Integer32
                }

    hwXQoSIfLrDiscardAlarmIfIndex OBJECT-TYPE
        SYNTAX InterfaceIndex
        MAX-ACCESS read-only
        STATUS current
        DESCRIPTION
            "The index of physical interface."
        ::= { hwXQoSIfLrDiscardAlarmEntry 1 }

    hwXQoSIfLrDiscardAlarmIfName OBJECT-TYPE
        SYNTAX OCTET STRING
        MAX-ACCESS read-only
        STATUS current
        DESCRIPTION
            "The name of physical interface."
        ::= { hwXQoSIfLrDiscardAlarmEntry 2 }

    hwXQoSIfLrDiscardAlarmCir OBJECT-TYPE
        SYNTAX Integer32
        MAX-ACCESS read-only
        STATUS current
        DESCRIPTION
            "This value of this object identifies the configured CIR."
        ::= { hwXQoSIfLrDiscardAlarmEntry 3 }

    hwXQoSIfLrDiscardAlarmTrapThreshold OBJECT-TYPE
        SYNTAX Integer32
        MAX-ACCESS read-only
        STATUS current
        DESCRIPTION
            "The threshold of the alarm."
        ::= { hwXQoSIfLrDiscardAlarmEntry 4 }

    hwXQoSIfLrDiscardAlarmPassPacketRate OBJECT-TYPE
        SYNTAX Integer32
        MAX-ACCESS read-only
        STATUS current
        DESCRIPTION
            "Pass packet rate."
        ::= { hwXQoSIfLrDiscardAlarmEntry 5 }

 --port queue alarm
    hwXQoSStatResouceNotEnoughAlarmTable OBJECT-TYPE
        SYNTAX SEQUENCE OF HwXQoSStatResouceNotEnoughAlarmEntry
        MAX-ACCESS not-accessible
        STATUS current
        DESCRIPTION
                "hwXQoSStatResouceNotEnoughAlarmTable"
        ::= { hwXQoSResouceNotEnoughAlarmObjects 1 }

    hwXQoSStatResouceNotEnoughAlarmEntry OBJECT-TYPE
        SYNTAX HwXQoSStatResouceNotEnoughAlarmEntry
        MAX-ACCESS not-accessible
        STATUS current
        DESCRIPTION
            "hwXQoSStatResouceNotEnoughAlarmEntry"
        INDEX { hwXQoSStatResouceNotEnoughSlotId, hwXQoSStatResouceNotEnoughStatType }
        ::= { hwXQoSStatResouceNotEnoughAlarmTable 1 }

    HwXQoSStatResouceNotEnoughAlarmEntry ::=
        SEQUENCE {
            hwXQoSStatResouceNotEnoughSlotId
                Integer32,
            hwXQoSStatResouceNotEnoughStatType
                OCTET STRING
            }

    hwXQoSStatResouceNotEnoughSlotId OBJECT-TYPE
        SYNTAX Integer32 (1..128)
        MAX-ACCESS read-only
        STATUS current
        DESCRIPTION
            "Slot ID of the LPU where the stastitics resource is insufficient"
        ::= { hwXQoSStatResouceNotEnoughAlarmEntry 1 }

    hwXQoSStatResouceNotEnoughStatType OBJECT-TYPE
        SYNTAX OCTET STRING (SIZE (1..511))
        MAX-ACCESS read-only
        STATUS current
        DESCRIPTION
            "Type of insufficient statistics resource"
        ::= { hwXQoSStatResouceNotEnoughAlarmEntry 2 }

    hwXQoSCARResouceNotEnoughAlarmTable OBJECT-TYPE
        SYNTAX SEQUENCE OF HwXQoSCARResouceNotEnoughAlarmEntry
        MAX-ACCESS not-accessible
        STATUS current
        DESCRIPTION
            "hwXQoSCARResouceNotEnoughAlarmTable"
        ::= { hwXQoSResouceNotEnoughAlarmObjects 2 }

    hwXQoSCARResouceNotEnoughAlarmEntry OBJECT-TYPE
        SYNTAX HwXQoSCARResouceNotEnoughAlarmEntry
        MAX-ACCESS not-accessible
        STATUS current
        DESCRIPTION
            "hwXQoSCARResouceNotEnoughAlarmEntry"
        INDEX { hwXQoSCARResouceNotEnoughSlotId, hwXQoSCARResouceNotEnoughCARType }
        ::= { hwXQoSCARResouceNotEnoughAlarmTable 1 }

    HwXQoSCARResouceNotEnoughAlarmEntry ::=
        SEQUENCE {
            hwXQoSCARResouceNotEnoughSlotId
                Integer32,
            hwXQoSCARResouceNotEnoughCARType
                OCTET STRING
                }

    hwXQoSCARResouceNotEnoughSlotId OBJECT-TYPE
        SYNTAX Integer32 (1..128)
        MAX-ACCESS read-only
        STATUS current
        DESCRIPTION
            "Slot ID of the LPU where the CAR resource is insufficient"
        ::= { hwXQoSCARResouceNotEnoughAlarmEntry 1 }

    hwXQoSCARResouceNotEnoughCARType OBJECT-TYPE
        SYNTAX OCTET STRING (SIZE (1..511))
        MAX-ACCESS read-only
        STATUS current
        DESCRIPTION
            "Type of insufficient car resource"
        ::= { hwXQoSCARResouceNotEnoughAlarmEntry 2 }

--begin add by jinxiaoyan
--hard-pipe alarm
    -- 1.3.6.1.4.1.2011.5.25.32.4.1.23
    hwXQoSHardPipeAlarmObjects OBJECT IDENTIFIER ::= { hwXQoSObjects 23 }

    -- 1.3.6.1.4.1.2011.5.25.32.4.1.23.1
    hwXQoSHardPipeAlarmTable OBJECT-TYPE
        SYNTAX SEQUENCE OF HwXQoSHardPipeAlarmEntry
        MAX-ACCESS not-accessible
        STATUS current
        DESCRIPTION
            "This table displays the bandwidth usage of the hard pipe."
        ::= { hwXQoSHardPipeAlarmObjects 1 }

    -- 1.3.6.1.4.1.2011.5.25.32.4.1.23.1.1
    hwXQoSHardPipeAlarmEntry OBJECT-TYPE
        SYNTAX HwXQoSHardPipeAlarmEntry
        MAX-ACCESS not-accessible
        STATUS current
        DESCRIPTION
            "hwXQoSHardPipeAlarmEntry"
        INDEX { hwXQoSHardPipeAlarmIfIndex }
        ::= { hwXQoSHardPipeAlarmTable 1 }

    HwXQoSHardPipeAlarmEntry ::=
        SEQUENCE {
            hwXQoSHardPipeAlarmIfIndex
                OCTET STRING,
            hwXQoSHardPipeAlarmUsage
            Integer32
            }

    -- 1.3.6.1.4.1.2011.5.25.32.4.1.23.1.1.1
    hwXQoSHardPipeAlarmIfIndex OBJECT-TYPE
        SYNTAX OCTET STRING
        MAX-ACCESS read-only
        STATUS current
        DESCRIPTION
            "The interface index."
        ::= { hwXQoSHardPipeAlarmEntry 1 }

    -- 1.3.6.1.4.1.2011.5.25.32.4.1.23.1.1.2
    hwXQoSHardPipeAlarmUsage OBJECT-TYPE
        SYNTAX Integer32
        MAX-ACCESS read-only
        STATUS current
        DESCRIPTION
            "The usage of qos hard-pipe bandwidth."
        ::= { hwXQoSHardPipeAlarmEntry 2 }

--end add by jinxiaoyan

--begin add by lidapeng
    -- 1.3.6.1.4.1.2011.5.25.32.4.1.23.3
    hwXQoSHardPipeApplySQFailAlarmTable OBJECT-TYPE
        SYNTAX SEQUENCE OF HwXQoSHardPipeApplySQFailAlarmEntry
        MAX-ACCESS not-accessible
        STATUS current
        DESCRIPTION
            "This table displays SQID resource application failure alarm."
        ::= { hwXQoSHardPipeAlarmObjects 3 }

    -- 1.3.6.1.4.1.2011.5.25.32.4.1.23.3.1
    hwXQoSHardPipeApplySQFailAlarmEntry OBJECT-TYPE
        SYNTAX HwXQoSHardPipeApplySQFailAlarmEntry
        MAX-ACCESS not-accessible
        STATUS current
        DESCRIPTION
            "hwXQoSHardPipeApplySQFailAlarmEntry"
        INDEX { hwXQoSHardPipeApplySQFailAlarmIfIndex }
        ::= { hwXQoSHardPipeApplySQFailAlarmTable 1 }

    HwXQoSHardPipeApplySQFailAlarmEntry ::=
        SEQUENCE {
            hwXQoSHardPipeApplySQFailAlarmIfIndex
                OCTET STRING
            }

    -- 1.3.6.1.4.1.2011.5.25.32.4.1.23.3.1.1
    hwXQoSHardPipeApplySQFailAlarmIfIndex OBJECT-TYPE
        SYNTAX OCTET STRING
        MAX-ACCESS read-only
        STATUS current
        DESCRIPTION
            "The interface index."
        ::= { hwXQoSHardPipeApplySQFailAlarmEntry 1 }

--begin add by gaolikun
    -- 1.3.6.1.4.1.2011.5.25.32.4.1.58
    hwXQoSTMPerformanceAlarmObjects OBJECT IDENTIFIER ::= { hwXQoSObjects 58 }

    -- 1.3.6.1.4.1.2011.5.25.32.4.1.58.1
    hwXQoSTMPerformanceAlarmTable OBJECT-TYPE
        SYNTAX SEQUENCE OF HwXQoSTMPerformanceAlarmEntry
        MAX-ACCESS not-accessible
        STATUS current
        DESCRIPTION
            "hwXQoSTMPerformanceAlarmTable"
        ::= { hwXQoSTMPerformanceAlarmObjects 1 }

    -- 1.3.6.1.4.1.2011.5.25.32.4.1.58.1.1
    hwXQoSTMPerformanceAlarmEntry OBJECT-TYPE
        SYNTAX HwXQoSTMPerformanceAlarmEntry
        MAX-ACCESS not-accessible
        STATUS current
        DESCRIPTION
            "hwXQoSTMPerformanceAlarmEntry"
        INDEX { hwXQoSTMPerformanceAlarmSlotId, hwXQoSTMPerformanceAlarmChipId }
        ::= { hwXQoSTMPerformanceAlarmTable 1 }

    HwXQoSTMPerformanceAlarmEntry ::=
        SEQUENCE {
            hwXQoSTMPerformanceAlarmSlotId
                OCTET STRING,
            hwXQoSTMPerformanceAlarmChipId
                Integer32
                }

    -- 1.3.6.1.4.1.2011.5.25.32.4.1.58.1.1.1
    hwXQoSTMPerformanceAlarmSlotId OBJECT-TYPE
        SYNTAX OCTET STRING
        MAX-ACCESS read-only
        STATUS current
        DESCRIPTION
            "The information of the slot."
        ::= { hwXQoSTMPerformanceAlarmEntry 1 }

    -- 1.3.6.1.4.1.2011.5.25.32.4.1.58.1.1.2
    hwXQoSTMPerformanceAlarmChipId OBJECT-TYPE
        SYNTAX Integer32
        MAX-ACCESS read-only
        STATUS current
        DESCRIPTION
            "The information of the chip."
        ::= { hwXQoSTMPerformanceAlarmEntry 2 }

--end add by gaolikun

--begin add by guohongbo
--modechannel bandwidth alarm
    -- 1.3.6.1.4.1.2011.5.25.32.4.1.68
    hwXQoSModeChannelOverPortShapAlarmObjects OBJECT IDENTIFIER ::= { hwXQoSObjects 68 }

    -- 1.3.6.1.4.1.2011.5.25.32.4.1.68.1
    hwXQoSModeChannelOverPortShapAlarmTable OBJECT-TYPE
        SYNTAX SEQUENCE OF HwXQoSModeChannelOverPortShapAlarmEntry
        MAX-ACCESS not-accessible
        STATUS current
        DESCRIPTION
            "This table displays alarms for the mode channel bandwidth over port shaping verification."
        ::= { hwXQoSModeChannelOverPortShapAlarmObjects 1 }

    -- 1.3.6.1.4.1.2011.5.25.32.4.1.68.1.1
    hwXQoSModeChannelOverPortShapAlarmEntry OBJECT-TYPE
        SYNTAX HwXQoSModeChannelOverPortShapAlarmEntry
        MAX-ACCESS not-accessible
        STATUS current
        DESCRIPTION
            "The mode channel bandwidth over port shaping alarm entry."
        INDEX { hwXQoSModeChannelOverPortShapAlarmIfIndex }
        ::= { hwXQoSModeChannelOverPortShapAlarmTable 1}

    HwXQoSModeChannelOverPortShapAlarmEntry ::=
        SEQUENCE{
            hwXQoSModeChannelOverPortShapAlarmIfIndex
                OCTET STRING
            }

    -- 1.3.6.1.4.1.2011.5.25.32.4.1.68.1.1.1
    hwXQoSModeChannelOverPortShapAlarmIfIndex OBJECT-TYPE
        SYNTAX OCTET STRING
        MAX-ACCESS read-only
        STATUS current
        DESCRIPTION
            "The mode channel bandwidth over port shaping alarm interface index."
        ::= { hwXQoSModeChannelOverPortShapAlarmEntry 1 }

--end add by guohongbo

--begin add by tanyashi
--mode flexe bandwidth alarm
    -- 1.3.6.1.4.1.2011.5.25.32.4.1.127
    hwXQoSModeFlexeOverPortShapAlarmObjects OBJECT IDENTIFIER ::= { hwXQoSObjects 127 }

    -- 1.3.6.1.4.1.2011.5.25.32.4.1.127.1
    hwXQoSModeFlexeOverPortShapAlarmTable OBJECT-TYPE
        SYNTAX SEQUENCE OF HwXQoSModeFlexeOverPortShapAlarmEntry
        MAX-ACCESS not-accessible
        STATUS current
        DESCRIPTION
            "This table displays alarms for the mode flexe bandwidth over port shaping verification."
        ::= { hwXQoSModeFlexeOverPortShapAlarmObjects 1 }

    -- 1.3.6.1.4.1.2011.5.25.32.4.1.127.1.1
    hwXQoSModeFlexeOverPortShapAlarmEntry OBJECT-TYPE
        SYNTAX HwXQoSModeFlexeOverPortShapAlarmEntry
        MAX-ACCESS not-accessible
        STATUS current
        DESCRIPTION
            "The mode flexe bandwidth over port shaping alarm entry."
        INDEX { hwXQoSModeFlexeOverPortShapAlarmIfIndex }
        ::= { hwXQoSModeFlexeOverPortShapAlarmTable 1}

    HwXQoSModeFlexeOverPortShapAlarmEntry ::=
        SEQUENCE{
            hwXQoSModeFlexeOverPortShapAlarmIfIndex
                OCTET STRING
            }

    -- 1.3.6.1.4.1.2011.5.25.32.4.1.127.1.1.1
    hwXQoSModeFlexeOverPortShapAlarmIfIndex OBJECT-TYPE
        SYNTAX OCTET STRING
        MAX-ACCESS read-only
        STATUS current
        DESCRIPTION
            "The mode flexe bandwidth over port shaping alarm interface index."
        ::= { hwXQoSModeFlexeOverPortShapAlarmEntry 1 }

--end add by tanyashi

--begin add by xuechenguang
--soft-pipe alarm
    -- 1.3.6.1.4.1.2011.5.25.32.4.1.41
    hwXQoSSoftPipeAlarmObjects OBJECT IDENTIFIER ::= { hwXQoSObjects 41 }

    -- 1.3.6.1.4.1.2011.5.25.32.4.1.41.1
    hwXQoSSoftPipeAlarmTable OBJECT-TYPE
        SYNTAX SEQUENCE OF HwXQoSSoftPipeAlarmEntry
        MAX-ACCESS not-accessible
        STATUS current
        DESCRIPTION
            "This table displays the bandwidth usage of the soft pipe."
        ::= { hwXQoSSoftPipeAlarmObjects 1 }

    -- 1.3.6.1.4.1.2011.5.25.32.4.1.41.1.1
    hwXQoSSoftPipeAlarmEntry OBJECT-TYPE
        SYNTAX HwXQoSSoftPipeAlarmEntry
        MAX-ACCESS not-accessible
        STATUS current
        DESCRIPTION
            "The softpipe alarm entry."
        INDEX { hwXQoSSoftPipeAlarmIfIndex }
        ::= { hwXQoSSoftPipeAlarmTable 1 }

    HwXQoSSoftPipeAlarmEntry ::=
        SEQUENCE {
            hwXQoSSoftPipeAlarmIfIndex
                OCTET STRING,
            hwXQoSSoftPipeAlarmUsage
            Integer32
            }

    -- 1.3.6.1.4.1.2011.5.25.32.4.1.41.1.1.1
    hwXQoSSoftPipeAlarmIfIndex OBJECT-TYPE
        SYNTAX OCTET STRING
        MAX-ACCESS read-only
        STATUS current
        DESCRIPTION
            "The soft pipe alarm interface index."
        ::= { hwXQoSSoftPipeAlarmEntry 1 }

    -- 1.3.6.1.4.1.2011.5.25.32.4.1.41.1.1.2
    hwXQoSSoftPipeAlarmUsage OBJECT-TYPE
        SYNTAX Integer32
        MAX-ACCESS read-only
        STATUS current
        DESCRIPTION
            "The usage of qos soft-pipe bandwidth."
        ::= { hwXQoSSoftPipeAlarmEntry 2 }

--end add by xuechenguang

--begin add by lizhen
--hardpipe bandwidth alarm
    -- 1.3.6.1.4.1.2011.5.25.32.4.1.47
    hwXQoSHardPipeBwAlarmObjects OBJECT IDENTIFIER ::= { hwXQoSObjects 47 }

    -- 1.3.6.1.4.1.2011.5.25.32.4.1.47.1
    hwXQoSHardPipeBwAlarmTable OBJECT-TYPE
        SYNTAX SEQUENCE OF HwXQoSHardPipeBwAlarmEntry
        MAX-ACCESS not-accessible
        STATUS current
        DESCRIPTION
            "This table displays alarms for the hard pipe bandwidth verification."
        ::= { hwXQoSHardPipeBwAlarmObjects 1 }

    -- 1.3.6.1.4.1.2011.5.25.32.4.1.47.1.1
    hwXQoSHardPipeBwAlarmEntry OBJECT-TYPE
        SYNTAX HwXQoSHardPipeBwAlarmEntry
        MAX-ACCESS not-accessible
        STATUS current
        DESCRIPTION
            "The hard pipe bandwidth alarm entry."
        INDEX { hwXQoSHardPipeBwAlarmIfIndex }
        ::= { hwXQoSHardPipeBwAlarmTable 1}

    HwXQoSHardPipeBwAlarmEntry ::=
        SEQUENCE{
            hwXQoSHardPipeBwAlarmIfIndex
                OCTET STRING,
            hwXQoSHardPipeBwAlarmResvBw
                Integer32
            }

    -- 1.3.6.1.4.1.2011.5.25.32.4.1.47.1.1.1
    hwXQoSHardPipeBwAlarmIfIndex OBJECT-TYPE
        SYNTAX OCTET STRING
        MAX-ACCESS read-only
        STATUS current
        DESCRIPTION
            "The hard pipe bandwidth alarm interface index."
        ::= { hwXQoSHardPipeBwAlarmEntry 1 }

    -- 1.3.6.1.4.1.2011.5.25.32.4.1.47.1.1.2
    hwXQoSHardPipeBwAlarmResvBw OBJECT-TYPE
        SYNTAX Integer32
        MAX-ACCESS read-only
        STATUS current
        DESCRIPTION
            "The soft pipe reserved bandwidth."
        ::= { hwXQoSHardPipeBwAlarmEntry 2 }
--end add by lizhen

--begin add by liuxiaoyan
--sq alarm
    -- 1.3.6.1.4.1.2011.5.25.32.4.1.25
    hwXQoSTrunkProfileNotEffectAlarmObjects OBJECT IDENTIFIER ::= { hwXQoSObjects 25 }

    -- 1.3.6.1.4.1.2011.5.25.32.4.1.25.1
    hwXQoSTrunkProfileNotEffectAlarmTable OBJECT-TYPE
        SYNTAX SEQUENCE OF HwXQoSTrunkProfileNotEffectAlarmEntry
        MAX-ACCESS not-accessible
        STATUS current
        DESCRIPTION
            "hwXQoSTrunkProfileNotEffectAlarmTable"
        ::= { hwXQoSTrunkProfileNotEffectAlarmObjects 1 }

    -- 1.3.6.1.4.1.2011.5.25.32.4.1.25.1.1
    hwXQoSTrunkProfileNotEffectAlarmEntry OBJECT-TYPE
        SYNTAX HwXQoSTrunkProfileNotEffectAlarmEntry
        MAX-ACCESS not-accessible
        STATUS current
        DESCRIPTION
            "hwXQoSTrunkProfileNotEffectAlarmEntry"
        INDEX { hwXQoSTrunkProfileNotEffectAlarmIfName , hwXQoSTrunkProfileNotEffectAlarmSlotid }
        ::= { hwXQoSTrunkProfileNotEffectAlarmTable 1 }

    HwXQoSTrunkProfileNotEffectAlarmEntry ::=
        SEQUENCE {
            hwXQoSTrunkProfileNotEffectAlarmIfName
                OCTET STRING,
            hwXQoSTrunkProfileNotEffectAlarmSlotid
                Integer32
            }

    -- 1.3.6.1.4.1.2011.5.25.32.4.1.25.1.1.1
    hwXQoSTrunkProfileNotEffectAlarmIfName OBJECT-TYPE
        SYNTAX OCTET STRING
        MAX-ACCESS read-only
        STATUS current
        DESCRIPTION
            "The interface name."
        ::= { hwXQoSTrunkProfileNotEffectAlarmEntry 1 }

    -- 1.3.6.1.4.1.2011.5.25.32.4.1.25.1.1.2
    hwXQoSTrunkProfileNotEffectAlarmSlotid OBJECT-TYPE
        SYNTAX Integer32
        MAX-ACCESS read-only
        STATUS current
        DESCRIPTION
            "The slotid of trunk member."
        ::= { hwXQoSTrunkProfileNotEffectAlarmEntry 2 }

--end add by liuxiaoyan

-- ******************************************************************
--   hwXQoSPortQueueStatisticsTable
--   hwXQoSQppbPolicyStatisticsTable
-- ******************************************************************

    hwXQoSQppbPolicyStatisticsTable OBJECT-TYPE
        SYNTAX      SEQUENCE OF HwXQoSQppbPolicyStatisticsEntry
        MAX-ACCESS  not-accessible
        STATUS      current
        DESCRIPTION
            " This table is used to display QPPB statistics."
        ::= { hwXQoSBaObjects 37 }

    hwXQoSQppbPolicyStatisticsEntry OBJECT-TYPE
        SYNTAX HwXQoSQppbPolicyStatisticsEntry
        MAX-ACCESS not-accessible
        STATUS current
        DESCRIPTION
            "hwXQoSQppbPolicyStatisticsEntry"
        INDEX  { hwXQoSQppbPolicyLocalID,
                hwXQoSQppbPolicyDirection,
                hwXQoSQppbPolicyStatisticsInterfaceIndex }
        ::= { hwXQoSQppbPolicyStatisticsTable 1 }

    HwXQoSQppbPolicyStatisticsEntry ::=
    SEQUENCE {
            hwXQoSQppbPolicyLocalID
                Integer32,
            hwXQoSQppbPolicyDirection
                INTEGER,
            hwXQoSQppbPolicyStatisticsInterfaceIndex
                InterfaceIndex,
            hwXQoSQppbPolicyStatisticsReset
                INTEGER,
            hwXQoSQppbPolicyMatchedPackets
                Counter64,
            hwXQoSQppbPolicyMatchedBytes
                Counter64,
            hwXQoSQppbPolicyPassedPackets
                Counter64,
            hwXQoSQppbPolicyPassedBytes
                Counter64,
            hwXQoSQppbPolicyDropedPackets
                Counter64,
            hwXQoSQppbPolicyDropedBytes
                Counter64,
            -- begin by chenzhe for qppb stat
            hwXQoSQppbPolicyMatchPacketsRate
                Counter64,
            hwXQoSQppbPolicyMatchBytesRate
                Counter64
        -- end by chenzhe for qppb stat
                            }

    hwXQoSQppbPolicyLocalID  OBJECT-TYPE
        SYNTAX Integer32
        MAX-ACCESS read-only
        STATUS current
        DESCRIPTION
            "This object indicates the qos-local-id."
        ::= { hwXQoSQppbPolicyStatisticsEntry 1 }

    hwXQoSQppbPolicyDirection  OBJECT-TYPE
        SYNTAX INTEGER
            {
            inbound(1),
            outbound(2)
            }
        MAX-ACCESS read-only
        STATUS current
        DESCRIPTION
            " This object indicates the direction where statistics are queried.
                The value can be:
                1: inbound
                2: outbound  "
        ::= { hwXQoSQppbPolicyStatisticsEntry 2 }

    hwXQoSQppbPolicyStatisticsInterfaceIndex  OBJECT-TYPE
        SYNTAX   InterfaceIndex
        MAX-ACCESS read-only
        STATUS current
        DESCRIPTION
            " This object indicates the index of the interface where statistics are queried. "
        ::= { hwXQoSQppbPolicyStatisticsEntry 3 }

    hwXQoSQppbPolicyStatisticsReset  OBJECT-TYPE
        SYNTAX INTEGER
        {
            reset(1)
        }
        MAX-ACCESS read-write
        STATUS current
        DESCRIPTION
            " This object indicates the statistics are reset.  "
        ::= { hwXQoSQppbPolicyStatisticsEntry 4 }

    hwXQoSQppbPolicyMatchedPackets OBJECT-TYPE
        SYNTAX  Counter64
        MAX-ACCESS read-only
        STATUS current
        DESCRIPTION
            " This object indicates the number of packets matching the QPPB policy. "
        ::= { hwXQoSQppbPolicyStatisticsEntry 5 }

    hwXQoSQppbPolicyMatchedBytes OBJECT-TYPE
        SYNTAX  Counter64
        MAX-ACCESS read-only
        STATUS current
        DESCRIPTION
            " This object indicates the number of matched bytes. "
        ::= { hwXQoSQppbPolicyStatisticsEntry 6 }

    hwXQoSQppbPolicyPassedPackets OBJECT-TYPE
        SYNTAX  Counter64
        MAX-ACCESS read-only
        STATUS current
        DESCRIPTION
            " This object indicates the number of forwarded packets. "
        ::= { hwXQoSQppbPolicyStatisticsEntry 7 }

    hwXQoSQppbPolicyPassedBytes OBJECT-TYPE
        SYNTAX  Counter64
        MAX-ACCESS read-only
        STATUS current
        DESCRIPTION
            " This object indicates the number of passed bytes. "
        ::= { hwXQoSQppbPolicyStatisticsEntry 8 }

    hwXQoSQppbPolicyDropedPackets OBJECT-TYPE
        SYNTAX  Counter64
        MAX-ACCESS read-only
        STATUS current
        DESCRIPTION
            " This object indicates the number of discarded packets. "
        ::= { hwXQoSQppbPolicyStatisticsEntry 9 }

    hwXQoSQppbPolicyDropedBytes OBJECT-TYPE
        SYNTAX  Counter64
        MAX-ACCESS read-only
        STATUS current
        DESCRIPTION
            " This object indicates the number of droped bytes. "
        ::= { hwXQoSQppbPolicyStatisticsEntry 10 }
--   begin by chenzhe for qppb stat
    hwXQoSQppbPolicyMatchPacketsRate OBJECT-TYPE
        SYNTAX  Counter64
        MAX-ACCESS read-only
        STATUS current
        DESCRIPTION
            "This object indicates the rate of packets matching the QPPB policy. "
        ::= { hwXQoSQppbPolicyStatisticsEntry 11 }


    hwXQoSQppbPolicyMatchBytesRate OBJECT-TYPE
        SYNTAX  Counter64
        MAX-ACCESS read-only
        STATUS current
        DESCRIPTION
            " This object indicates the rate of matched bytes. "
        ::= { hwXQoSQppbPolicyStatisticsEntry 12 }

--   end by chenzhe for qppb stat

    hwXQoSIfPhbEnableTable OBJECT-TYPE
        SYNTAX SEQUENCE OF HwXQoSIfPhbEnableEntry
        MAX-ACCESS not-accessible
        STATUS current
        DESCRIPTION
            "qos phb enable <domain-name> [ vlan ] [vlan-id]."
        ::= { hwXQoSBaObjects 38 }

    hwXQoSIfPhbEnableEntry OBJECT-TYPE
        SYNTAX HwXQoSIfPhbEnableEntry
        MAX-ACCESS not-accessible
        STATUS current
        DESCRIPTION
            "hwXQoSIfPhbEnableEntry."
        INDEX { hwXQoSIfPhbEnableIfIndex, hwXQoSIfPhbEnableVlanId }
        ::= { hwXQoSIfPhbEnableTable 1 }

    HwXQoSIfPhbEnableEntry ::=
    SEQUENCE {
        hwXQoSIfPhbEnableIfIndex
            Integer32,
        hwXQoSIfPhbEnableVlanId
            Integer32,
        hwXQoSIfPhbEnableDomainName
            OCTET STRING,
        hwXQoSIfPhbEnableRowStatus
            RowStatus
        }

    hwXQoSIfPhbEnableIfIndex OBJECT-TYPE
        SYNTAX Integer32
        MAX-ACCESS read-only
        STATUS current
        DESCRIPTION
            "The value of this object identifies the interface index."
        ::= { hwXQoSIfPhbEnableEntry 1 }

    hwXQoSIfPhbEnableVlanId OBJECT-TYPE
        SYNTAX Integer32 (0 | 1..4094)
        MAX-ACCESS read-only
        STATUS current
        DESCRIPTION
            "The value of this object identifies the VLAN ID of the interface."
        ::= { hwXQoSIfPhbEnableEntry 2 }

    hwXQoSIfPhbEnableDomainName OBJECT-TYPE
        SYNTAX OCTET STRING (SIZE (1..31))
        MAX-ACCESS read-create
        STATUS current
        DESCRIPTION
            "This object indicates the name of the DS domain. The value of the object ranges from 1 to 31. The name cannot contain Chinese characters."
        ::= { hwXQoSIfPhbEnableEntry 3 }


    hwXQoSIfPhbEnableRowStatus OBJECT-TYPE
        SYNTAX RowStatus
        MAX-ACCESS read-create
        STATUS current
        DESCRIPTION
            "This value of this object identifies the row status. The value can be any of the following: CreateAndGo(4), Destroy(6), Active(1)."
        ::= { hwXQoSIfPhbEnableEntry 4 }

    hwXQoSIfRemarkDscpTable OBJECT-TYPE
        SYNTAX SEQUENCE OF HwXQoSIfRemarkDscpEntry
        MAX-ACCESS not-accessible
        STATUS current
        DESCRIPTION
            "enable to remark DSCP of the payload. "
        ::= { hwXQoSBaObjects 39 }

    hwXQoSIfRemarkDscpEntry OBJECT-TYPE
        SYNTAX HwXQoSIfRemarkDscpEntry
        MAX-ACCESS not-accessible
        STATUS current
        DESCRIPTION
            "hwXQoSIfRemarkDscpEntry."
        INDEX { hwXQoSIfRemarkDscpIfIndex }
        ::= { hwXQoSIfRemarkDscpTable 1 }

    HwXQoSIfRemarkDscpEntry ::=
    SEQUENCE {
        hwXQoSIfRemarkDscpIfIndex
            Integer32,
        hwXQoSIfRemarkDscpRowStatus
            RowStatus
        }

    hwXQoSIfRemarkDscpIfIndex OBJECT-TYPE
        SYNTAX Integer32
        MAX-ACCESS read-only
        STATUS current
        DESCRIPTION
            "The value of this object identifies the interface index."
        ::= { hwXQoSIfRemarkDscpEntry 1 }

        hwXQoSIfRemarkDscpRowStatus OBJECT-TYPE
        SYNTAX RowStatus
        MAX-ACCESS read-create
        STATUS current
        DESCRIPTION
            "This value of this object identifies the row status. The value can be any of the following: CreateAndGo(4), Destroy(6), Active(1)."
        ::= { hwXQoSIfRemarkDscpEntry 2 }

-- ******************************************************************
--   hwXQoSQppbGlobalStatisticsTable
-- ******************************************************************
    hwXQoSQppbGlobalStatisticsTable OBJECT-TYPE
        SYNTAX      SEQUENCE OF HwXQoSQppbGlobalStatisticsEntry
        MAX-ACCESS  not-accessible
        STATUS      current
        DESCRIPTION
            "This table displays global QPPB statistics. "
        ::= { hwXQoSBaObjects 40 }

    hwXQoSQppbGlobalStatisticsEntry OBJECT-TYPE
        SYNTAX HwXQoSQppbGlobalStatisticsEntry
        MAX-ACCESS not-accessible
        STATUS current
        DESCRIPTION
            "hwXQoSQppbGlobalStatisticsEntry"
        INDEX  { hwXQoSQppbGlobalStatisticsPolicyName,
                hwXQoSQppbGlobalStatisticsLocalID,
                hwXQoSQppbGlobalStatisticsDirection }
        ::= { hwXQoSQppbGlobalStatisticsTable 1 }

    HwXQoSQppbGlobalStatisticsEntry ::=
        SEQUENCE {
            hwXQoSQppbGlobalStatisticsPolicyName
                OCTET STRING,
            hwXQoSQppbGlobalStatisticsLocalID
                Integer32,
            hwXQoSQppbGlobalStatisticsDirection
                INTEGER,
            hwXQoSQppbGlobalStatisticsReset
                INTEGER,
            hwXQoSQppbGlobalStatisticsMatchedPackets
                Counter64,
            hwXQoSQppbGlobalStatisticsMatchedBytes
                Counter64,
            hwXQoSQppbGlobalStatisticsPassedPackets
                Counter64,
            hwXQoSQppbGlobalStatisticsPassedBytes
                Counter64,
            hwXQoSQppbGlobalStatisticsDropedPackets
                Counter64,
            hwXQoSQppbGlobalStatisticsDropedBytes
                Counter64,
            hwXQoSQppbGlobalStatisticsMatchPacketsRate
                Counter64,
            hwXQoSQppbGlobalStatisticsMatchBytesRate
                Counter64
                }

    hwXQoSQppbGlobalStatisticsPolicyName  OBJECT-TYPE
        SYNTAX   OCTET STRING (SIZE (1..31))
        MAX-ACCESS read-only
        STATUS current
        DESCRIPTION
            " This object indicates the name of a QPPB policy. "
        ::= { hwXQoSQppbGlobalStatisticsEntry 1 }

    hwXQoSQppbGlobalStatisticsLocalID  OBJECT-TYPE
        SYNTAX Integer32
        MAX-ACCESS read-only
        STATUS current
        DESCRIPTION
            "This object indicates the qos-local-id ."
        ::= { hwXQoSQppbGlobalStatisticsEntry 2 }

    hwXQoSQppbGlobalStatisticsDirection  OBJECT-TYPE
        SYNTAX INTEGER
            {
            inbound(1),
            outbound(2)
            }
        MAX-ACCESS read-only
        STATUS current
        DESCRIPTION
            " This object indicates the traffic direction for which global QPPB statistics are queried.
                The value can be one of the following:
                inbound (1)
                outbound (2).  "
        ::= { hwXQoSQppbGlobalStatisticsEntry 3 }

    hwXQoSQppbGlobalStatisticsReset  OBJECT-TYPE
        SYNTAX INTEGER
        {
            reset(1)
        }
        MAX-ACCESS read-write
        STATUS current
        DESCRIPTION
            " This object indicates the statistics are reset.  "
        ::= { hwXQoSQppbGlobalStatisticsEntry 4 }

    hwXQoSQppbGlobalStatisticsMatchedPackets OBJECT-TYPE
        SYNTAX  Counter64
        MAX-ACCESS read-only
        STATUS current
        DESCRIPTION
            " This object indicates the number of packets matching the QPPB policy. "
        ::= { hwXQoSQppbGlobalStatisticsEntry 5 }

    hwXQoSQppbGlobalStatisticsMatchedBytes OBJECT-TYPE
        SYNTAX  Counter64
        MAX-ACCESS read-only
        STATUS current
        DESCRIPTION
            " This object indicates the number of matched bytes. "
        ::= { hwXQoSQppbGlobalStatisticsEntry 6 }

    hwXQoSQppbGlobalStatisticsPassedPackets OBJECT-TYPE
        SYNTAX  Counter64
        MAX-ACCESS read-only
        STATUS current
        DESCRIPTION
            " hwXQoSQppbGlobalStatisticsPassedPackets. "
        ::= { hwXQoSQppbGlobalStatisticsEntry 7 }

    hwXQoSQppbGlobalStatisticsPassedBytes OBJECT-TYPE
        SYNTAX  Counter64
        MAX-ACCESS read-only
        STATUS current
        DESCRIPTION
            " This object indicates the number of passed bytes. "
        ::= { hwXQoSQppbGlobalStatisticsEntry 8 }

    hwXQoSQppbGlobalStatisticsDropedPackets OBJECT-TYPE
        SYNTAX  Counter64
        MAX-ACCESS read-only
        STATUS current
        DESCRIPTION
            " This object indicates the number of discarded packets. "
        ::= { hwXQoSQppbGlobalStatisticsEntry 9 }

    hwXQoSQppbGlobalStatisticsDropedBytes OBJECT-TYPE
        SYNTAX  Counter64
        MAX-ACCESS read-only
        STATUS current
        DESCRIPTION
            " This object indicates the number of droped bytes. "
        ::= { hwXQoSQppbGlobalStatisticsEntry 10 }

    hwXQoSQppbGlobalStatisticsMatchPacketsRate OBJECT-TYPE
        SYNTAX  Counter64
        MAX-ACCESS read-only
        STATUS current
        DESCRIPTION
            " This object indicates the rate of packets matching the QPPB policy. "
        ::= { hwXQoSQppbGlobalStatisticsEntry 11 }

    hwXQoSQppbGlobalStatisticsMatchBytesRate OBJECT-TYPE
        SYNTAX  Counter64
        MAX-ACCESS read-only
        STATUS current
        DESCRIPTION
            " This object indicates the rate of matched bytes. "
        ::= { hwXQoSQppbGlobalStatisticsEntry 12 }
--add by wangfengli
-- ******************************************************************
--
--   hwXQoSHardPipeStatisticsTable
--
-- ******************************************************************

    hwXQoSHardPipeStatisticsTable OBJECT-TYPE
        SYNTAX      SEQUENCE OF HwXQoSHardPipeStatisticsEntry
        MAX-ACCESS  not-accessible
        STATUS      current
        DESCRIPTION
            " This table is used to display statistics about outgoing packets on the PW-side and AC-side hard pipe. "
        ::= { hwXQoSBaObjects 41 }


    hwXQoSHardPipeStatisticsEntry OBJECT-TYPE
        SYNTAX HwXQoSHardPipeStatisticsEntry
        MAX-ACCESS not-accessible
        STATUS current
        DESCRIPTION
            " This table is used to query the statistics of hard pipe statistics. "
        INDEX  { hwXQoSHardPipeStatisticsInterfaceIndex}
        ::= { hwXQoSHardPipeStatisticsTable 1 }

    HwXQoSHardPipeStatisticsEntry ::=
    SEQUENCE {
        hwXQoSHardPipeStatisticsInterfaceIndex
            InterfaceIndex,
        hwXQoSHardPipeStatisticsReset
            INTEGER,
        hwXQoSHardPipeStatisticsPassPackets
            Counter64,
        hwXQoSHardPipeStatisticsPassBytes
            Counter64,
        hwXQoSHardPipeStatisticsDiscardPackets
            Counter64,
        hwXQoSHardPipeStatisticsDiscardBytes
            Counter64,
        hwXQoSHardPipeStatisticsPassPacketsRate
            Counter64,
        hwXQoSHardPipeStatisticsPassBytesRate
            Counter64,
        hwXQoSHardPipeStatisticsDiscardPacketsRate
            Counter64,
        hwXQoSHardPipeStatisticsDiscardBytesRate
            Counter64
            }

    hwXQoSHardPipeStatisticsInterfaceIndex  OBJECT-TYPE
        SYNTAX   InterfaceIndex
        MAX-ACCESS read-only
        STATUS current
        DESCRIPTION
            " This object indicates the hard pipe interface. "
        ::= { hwXQoSHardPipeStatisticsEntry 1 }

    hwXQoSHardPipeStatisticsReset  OBJECT-TYPE
        SYNTAX INTEGER
        {
            reset(1)
        }
        MAX-ACCESS read-create
        STATUS current
        DESCRIPTION
            " This object indicates the flag of clearing hard pipe traffic statistics.  "
        ::= { hwXQoSHardPipeStatisticsEntry 2 }

    hwXQoSHardPipeStatisticsPassPackets OBJECT-TYPE
        SYNTAX  Counter64
        MAX-ACCESS read-only
        STATUS current
        DESCRIPTION
            " This object indicates the number of packets forwarded by the hard pipe. "
        ::= { hwXQoSHardPipeStatisticsEntry 3 }

    hwXQoSHardPipeStatisticsPassBytes OBJECT-TYPE
        SYNTAX  Counter64
        MAX-ACCESS read-only
        STATUS current
        DESCRIPTION
            " This object indicates the number of  passed bytes. "
        ::= { hwXQoSHardPipeStatisticsEntry 4 }

    hwXQoSHardPipeStatisticsDiscardPackets OBJECT-TYPE
        SYNTAX  Counter64
        MAX-ACCESS read-only
        STATUS current
        DESCRIPTION
            " This object indicates the number of packets discarded by the hard pipe."
        ::= { hwXQoSHardPipeStatisticsEntry 5 }

    hwXQoSHardPipeStatisticsDiscardBytes OBJECT-TYPE
        SYNTAX  Counter64
        MAX-ACCESS read-only
        STATUS current
        DESCRIPTION
            " This object indicates the number of discarded bytes. "
        ::= { hwXQoSHardPipeStatisticsEntry 6 }

    hwXQoSHardPipeStatisticsPassPacketsRate OBJECT-TYPE
        SYNTAX  Counter64
        MAX-ACCESS read-only
        STATUS current
        DESCRIPTION
            " This object indicates the rate at which the hard pipe forwards packets."
        ::= { hwXQoSHardPipeStatisticsEntry 7 }

    hwXQoSHardPipeStatisticsPassBytesRate OBJECT-TYPE
        SYNTAX  Counter64
        MAX-ACCESS read-only
        STATUS current
        DESCRIPTION
            " The value of this object identifies the rate of pass bytes. "
        ::= { hwXQoSHardPipeStatisticsEntry 8 }

    hwXQoSHardPipeStatisticsDiscardPacketsRate OBJECT-TYPE
        SYNTAX  Counter64
        MAX-ACCESS read-only
        STATUS current
        DESCRIPTION
            " This object indicates the rate at which the hard pipe discards packets."
        ::= { hwXQoSHardPipeStatisticsEntry 9 }

    hwXQoSHardPipeStatisticsDiscardBytesRate OBJECT-TYPE
        SYNTAX  Counter64
        MAX-ACCESS read-only
        STATUS current
        DESCRIPTION
            " The value of this object identifies the rate of discarded bytes."
        ::= { hwXQoSHardPipeStatisticsEntry 10 }

-- end by wangfengli
--add by sunhongliang
-- ******************************************************************
--
--   hwXQoSHardPipeConfigTable
--
-- ******************************************************************

    hwXQoSHardPipeConfigTable OBJECT-TYPE
        SYNTAX      SEQUENCE OF HwXQoSHardPipeConfigEntry
        MAX-ACCESS  not-accessible
        STATUS      current
        DESCRIPTION
            " This table is used to query the bandwidth of hard pipe config. "
        ::= { hwXQoSBaObjects 42}

    hwXQoSHardPipeConfigEntry OBJECT-TYPE
        SYNTAX HwXQoSHardPipeConfigEntry
        MAX-ACCESS not-accessible
        STATUS current
        DESCRIPTION
            " This table is used to query the bandwidth of hard pipe config. "
        INDEX  { hwXQoSHardPipeConfigInterfaceIndex}
        ::= { hwXQoSHardPipeConfigTable 1 }

    HwXQoSHardPipeConfigEntry ::=
        SEQUENCE {
            hwXQoSHardPipeConfigInterfaceIndex
                InterfaceIndex,
            hwXQoSHardPipeConfigBandwidth
                Integer32
            }

    hwXQoSHardPipeConfigInterfaceIndex  OBJECT-TYPE
        SYNTAX   InterfaceIndex
        MAX-ACCESS read-only
        STATUS current
        DESCRIPTION
            " This object indicates the interface index. "
        ::= { hwXQoSHardPipeConfigEntry 1 }

    hwXQoSHardPipeConfigBandwidth  OBJECT-TYPE
        SYNTAX  Integer32
        MAX-ACCESS read-only
        STATUS current
        DESCRIPTION
            " This object indicates the bandwidth of configed hard pipe. "
        ::= { hwXQoSHardPipeConfigEntry 2 }

-- end by sunhongliang
--add by sunhongliang
-- ******************************************************************
--
--   hwXQoSHardPipeAbilityTable
--
-- ******************************************************************

    hwXQoSHardPipeAbilityTable OBJECT-TYPE
        SYNTAX      SEQUENCE OF HwXQoSHardPipeAbilityEntry
        MAX-ACCESS  not-accessible
        STATUS      current
        DESCRIPTION
            " This table is used to query the  hard pipe ability of port. "
        ::= { hwXQoSBaObjects 43 }


    hwXQoSHardPipeAbilityEntry OBJECT-TYPE
        SYNTAX HwXQoSHardPipeAbilityEntry
        MAX-ACCESS not-accessible
        STATUS current
        DESCRIPTION
            " This table is used to query the  hard pipe ability of port. "
        INDEX  { hwXQoSHardPipeAbilityInterfaceIndex}
        ::= { hwXQoSHardPipeAbilityTable 1 }

    HwXQoSHardPipeAbilityEntry ::=
        SEQUENCE {
            hwXQoSHardPipeAbilityInterfaceIndex
                InterfaceIndex,
            hwXQoSHardPipeAbility
                INTEGER
            }

    hwXQoSHardPipeAbilityInterfaceIndex  OBJECT-TYPE
        SYNTAX   InterfaceIndex
        MAX-ACCESS read-only
        STATUS current
        DESCRIPTION
            " This object indicates the interface index. "
        ::= { hwXQoSHardPipeAbilityEntry 1 }

    hwXQoSHardPipeAbility  OBJECT-TYPE
        SYNTAX  INTEGER
        {
            none(1),
            unknown(2),
            sharemode(3),
            exclusivemode(4),
            needsplit(5)
        }
        MAX-ACCESS read-only
        STATUS current
        DESCRIPTION
            " This object indicates the hard pipe ability of port. "
        ::= { hwXQoSHardPipeAbilityEntry 2 }
--End by sunhongliang
--add by liangyun
-- ******************************************************************
--
--   hwXQoSHardPipeAccessStatisticsTable
--
-- ******************************************************************

    hwXQoSHardPipeAccessStatisticsTable OBJECT-TYPE
        SYNTAX      SEQUENCE OF HwXQoSHardPipeAccessStatisticsEntry
        MAX-ACCESS  not-accessible
        STATUS      current
        DESCRIPTION
            " This table is used to query the hard pipe statistics of access interface. "
        ::= { hwXQoSBaObjects 44 }


    hwXQoSHardPipeAccessStatisticsEntry OBJECT-TYPE
        SYNTAX HwXQoSHardPipeAccessStatisticsEntry
        MAX-ACCESS not-accessible
        STATUS current
        DESCRIPTION
            " This table is used to query the hard pipe statistics of access interface. "
        INDEX  { hwXQoSHardPipeAccessStatisticsInterfaceIndex,
                hwXQoSHardPipeAccessStatisticsDirection }
        ::= { hwXQoSHardPipeAccessStatisticsTable 1 }

    HwXQoSHardPipeAccessStatisticsEntry ::=
        SEQUENCE {
            hwXQoSHardPipeAccessStatisticsInterfaceIndex
                InterfaceIndex,
            hwXQoSHardPipeAccessStatisticsDirection
                INTEGER,
            hwXQoSHardPipeAccessStatisticsReset
                INTEGER,
            hwXQoSHardPipeAccessStatisticsPassPackets
                Counter64,
            hwXQoSHardPipeAccessStatisticsPassBytes
                Counter64,
            hwXQoSHardPipeAccessStatisticsDiscardPackets
                Counter64,
            hwXQoSHardPipeAccessStatisticsDiscardBytes
                Counter64,
            hwXQoSHardPipeAccessStatisticsPassPacketsRate
                Counter64,
            hwXQoSHardPipeAccessStatisticsPassBytesRate
                Counter64,
            hwXQoSHardPipeAccessStatisticsDiscardPacketsRate
                Counter64,
            hwXQoSHardPipeAccessStatisticsDiscardBytesRate
                Counter64
            }

    hwXQoSHardPipeAccessStatisticsInterfaceIndex  OBJECT-TYPE
        SYNTAX   InterfaceIndex
        MAX-ACCESS read-only
        STATUS current
        DESCRIPTION
            " This object indicates the access interface index. "
        ::= { hwXQoSHardPipeAccessStatisticsEntry 1 }

    hwXQoSHardPipeAccessStatisticsDirection  OBJECT-TYPE
        SYNTAX INTEGER
            {
            inbound(1),
            outbound(2)
            }
        MAX-ACCESS read-only
        STATUS current
        DESCRIPTION
            " This object indicates the direction where access hard pipe statistics are queried.
                The value can be:
                1: inbound
                2: outbound  "
        ::= { hwXQoSHardPipeAccessStatisticsEntry 2 }

    hwXQoSHardPipeAccessStatisticsReset  OBJECT-TYPE
        SYNTAX INTEGER
        {
            reset(1)
        }
        MAX-ACCESS read-write
        STATUS current
        DESCRIPTION
            " This object indicates the statistics are reset.  "
        ::= { hwXQoSHardPipeAccessStatisticsEntry 3 }

    hwXQoSHardPipeAccessStatisticsPassPackets OBJECT-TYPE
        SYNTAX  Counter64
        MAX-ACCESS read-only
        STATUS current
        DESCRIPTION
            " This object indicates the number of passed packets. "
        ::= { hwXQoSHardPipeAccessStatisticsEntry 4 }

    hwXQoSHardPipeAccessStatisticsPassBytes OBJECT-TYPE
        SYNTAX  Counter64
        MAX-ACCESS read-only
        STATUS current
        DESCRIPTION
            " This object indicates the number of  passed bytes. "
        ::= { hwXQoSHardPipeAccessStatisticsEntry 5 }

    hwXQoSHardPipeAccessStatisticsDiscardPackets OBJECT-TYPE
        SYNTAX  Counter64
        MAX-ACCESS read-only
        STATUS current
        DESCRIPTION
            " This object indicates the number of discarded packets."
        ::= { hwXQoSHardPipeAccessStatisticsEntry 6 }

    hwXQoSHardPipeAccessStatisticsDiscardBytes OBJECT-TYPE
        SYNTAX  Counter64
        MAX-ACCESS read-only
        STATUS current
        DESCRIPTION
            " This object indicates the number of discarded bytes. "
        ::= { hwXQoSHardPipeAccessStatisticsEntry 7 }

    hwXQoSHardPipeAccessStatisticsPassPacketsRate OBJECT-TYPE
        SYNTAX  Counter64
        MAX-ACCESS read-only
        STATUS current
        DESCRIPTION
            " The value of this object identifies the rate of pass packets."
        ::= { hwXQoSHardPipeAccessStatisticsEntry 8 }

    hwXQoSHardPipeAccessStatisticsPassBytesRate OBJECT-TYPE
        SYNTAX  Counter64
        MAX-ACCESS read-only
        STATUS current
        DESCRIPTION
            " The value of this object identifies the rate of pass bytes. "
        ::= { hwXQoSHardPipeAccessStatisticsEntry 9 }

    hwXQoSHardPipeAccessStatisticsDiscardPacketsRate OBJECT-TYPE
        SYNTAX  Counter64
        MAX-ACCESS read-only
        STATUS current
        DESCRIPTION
            " The value of this object identifies the rate of discarded packets."
        ::= { hwXQoSHardPipeAccessStatisticsEntry 10 }


    hwXQoSHardPipeAccessStatisticsDiscardBytesRate OBJECT-TYPE
        SYNTAX  Counter64
        MAX-ACCESS read-only
        STATUS current
        DESCRIPTION
            " The value of this object identifies the rate of discarded bytes."
        ::= { hwXQoSHardPipeAccessStatisticsEntry 11 }
--End by liangyun

    hwXQoSQppbPolicyStatisticsExtTable OBJECT-TYPE
        SYNTAX      SEQUENCE OF HwXQoSQppbPolicyStatisticsExtEntry
        MAX-ACCESS  not-accessible
        STATUS      current
        DESCRIPTION
            " This table is used to display QPPB statistics."
        ::= { hwXQoSBaObjects 45 }

    hwXQoSQppbPolicyStatisticsExtEntry OBJECT-TYPE
        SYNTAX HwXQoSQppbPolicyStatisticsExtEntry
        MAX-ACCESS not-accessible
        STATUS current
        DESCRIPTION
            "hwXQoSQppbPolicyStatisticsExtEntry"
        INDEX  { hwXQoSQppbPolicyStatisticsExtLocalID,
                hwXQoSQppbPolicyStatisticsExtDirection,
                hwXQoSQppbPolicyStatisticsExtInterfaceIndex }
        ::= { hwXQoSQppbPolicyStatisticsExtTable 1 }

    HwXQoSQppbPolicyStatisticsExtEntry ::=
        SEQUENCE {
            hwXQoSQppbPolicyStatisticsExtLocalID
                Integer32,
            hwXQoSQppbPolicyStatisticsExtDirection
                INTEGER,
            hwXQoSQppbPolicyStatisticsExtInterfaceIndex
                InterfaceIndex,
            hwXQoSQppbPolicyStatisticsExtReset
                INTEGER,
            hwXQoSQppbPolicyMatchedPacketsLow
                Unsigned32,
            hwXQoSQppbPolicyMatchedPacketsHigh
                Unsigned32,
            hwXQoSQppbPolicyMatchedBytesLow
                Unsigned32,
            hwXQoSQppbPolicyMatchedBytesHigh
                Unsigned32,
            hwXQoSQppbPolicyPassedPacketsLow
                Unsigned32,
            hwXQoSQppbPolicyPassedPacketsHigh
                Unsigned32,
            hwXQoSQppbPolicyPassedBytesLow
                Unsigned32,
            hwXQoSQppbPolicyPassedBytesHigh
                Unsigned32,
            hwXQoSQppbPolicyDropedPacketsLow
                Unsigned32,
            hwXQoSQppbPolicyDropedPacketsHigh
                Unsigned32,
            hwXQoSQppbPolicyDropedBytesLow
                Unsigned32,
            hwXQoSQppbPolicyDropedBytesHigh
                Unsigned32,
            hwXQoSQppbPolicyMatchPacketsRateLow
                Unsigned32,
            hwXQoSQppbPolicyMatchPacketsRateHigh
                Unsigned32,
            hwXQoSQppbPolicyMatchBytesRateLow
                Unsigned32,
            hwXQoSQppbPolicyMatchBytesRateHigh
                Unsigned32
                            }

    hwXQoSQppbPolicyStatisticsExtLocalID  OBJECT-TYPE
        SYNTAX Integer32
        MAX-ACCESS read-only
        STATUS current
        DESCRIPTION
            "This object indicates the qos-local-id."
        ::= { hwXQoSQppbPolicyStatisticsExtEntry 1 }

    hwXQoSQppbPolicyStatisticsExtDirection  OBJECT-TYPE
        SYNTAX INTEGER
            {
            inbound(1),
            outbound(2)
            }
        MAX-ACCESS read-only
        STATUS current
        DESCRIPTION
            " This object indicates the direction where statistics are queried.
                The value can be:
                1: inbound
                2: outbound  "
        ::= { hwXQoSQppbPolicyStatisticsExtEntry 2 }

    hwXQoSQppbPolicyStatisticsExtInterfaceIndex  OBJECT-TYPE
        SYNTAX   InterfaceIndex
        MAX-ACCESS read-only
        STATUS current
        DESCRIPTION
            " This object indicates the index of the interface where statistics are queried. "
        ::= { hwXQoSQppbPolicyStatisticsExtEntry 3 }

    hwXQoSQppbPolicyStatisticsExtReset  OBJECT-TYPE
        SYNTAX INTEGER
        {
            reset(1)
        }
        MAX-ACCESS read-write
        STATUS current
        DESCRIPTION
            " This object indicates the statistics are reset.  "
        ::= { hwXQoSQppbPolicyStatisticsExtEntry 4 }

    hwXQoSQppbPolicyMatchedPacketsLow OBJECT-TYPE
        SYNTAX  Unsigned32
        MAX-ACCESS read-only
        STATUS current
        DESCRIPTION
            " This object indicates the number of packets matching the QPPB policy, which is lower 32 bits of the total number. "
        ::= { hwXQoSQppbPolicyStatisticsExtEntry 5 }

    hwXQoSQppbPolicyMatchedPacketsHigh OBJECT-TYPE
        SYNTAX  Unsigned32
        MAX-ACCESS read-only
        STATUS current
        DESCRIPTION
            " This object indicates the number of packets matching the QPPB policy, which is upper 32 bits of the total number. "
        ::= { hwXQoSQppbPolicyStatisticsExtEntry 6 }

    hwXQoSQppbPolicyMatchedBytesLow OBJECT-TYPE
        SYNTAX  Unsigned32
        MAX-ACCESS read-only
        STATUS current
        DESCRIPTION
            " This object indicates the number of matched bytes, which is lower 32 bits of the total number. "
        ::= { hwXQoSQppbPolicyStatisticsExtEntry 7 }

    hwXQoSQppbPolicyMatchedBytesHigh OBJECT-TYPE
        SYNTAX  Unsigned32
        MAX-ACCESS read-only
        STATUS current
        DESCRIPTION
            " This object indicates the number of matched bytes, which is upper 32 bits of the total number. "
        ::= { hwXQoSQppbPolicyStatisticsExtEntry 8 }

    hwXQoSQppbPolicyPassedPacketsLow OBJECT-TYPE
        SYNTAX  Unsigned32
        MAX-ACCESS read-only
        STATUS current
        DESCRIPTION
            " This object indicates the number of forwarded packets, which is lower 32 bits of the total number. "
        ::= { hwXQoSQppbPolicyStatisticsExtEntry 9 }

    hwXQoSQppbPolicyPassedPacketsHigh OBJECT-TYPE
        SYNTAX  Unsigned32
        MAX-ACCESS read-only
        STATUS current
        DESCRIPTION
            " This object indicates the number of forwarded packets, which is upper 32 bits of the total number. "
        ::= { hwXQoSQppbPolicyStatisticsExtEntry 10 }

    hwXQoSQppbPolicyPassedBytesLow OBJECT-TYPE
        SYNTAX  Unsigned32
        MAX-ACCESS read-only
        STATUS current
        DESCRIPTION
            " This object indicates the number of passed bytes, which is lower 32 bits of the total number. "
        ::= { hwXQoSQppbPolicyStatisticsExtEntry 11 }

    hwXQoSQppbPolicyPassedBytesHigh OBJECT-TYPE
        SYNTAX  Unsigned32
        MAX-ACCESS read-only
        STATUS current
        DESCRIPTION
            " This object indicates the number of passed bytes, which is upper 32 bits of the total number. "
        ::= { hwXQoSQppbPolicyStatisticsExtEntry 12 }

    hwXQoSQppbPolicyDropedPacketsLow OBJECT-TYPE
        SYNTAX  Unsigned32
        MAX-ACCESS read-only
        STATUS current
        DESCRIPTION
            " This object indicates the number of discarded packets, which is lower 32 bits of the total number. "
        ::= { hwXQoSQppbPolicyStatisticsExtEntry 13 }

    hwXQoSQppbPolicyDropedPacketsHigh OBJECT-TYPE
        SYNTAX  Unsigned32
        MAX-ACCESS read-only
        STATUS current
        DESCRIPTION
            " This object indicates the number of discarded packets, which is upper 32 bits of the total number. "
        ::= { hwXQoSQppbPolicyStatisticsExtEntry 14 }

    hwXQoSQppbPolicyDropedBytesLow OBJECT-TYPE
        SYNTAX  Unsigned32
        MAX-ACCESS read-only
        STATUS current
        DESCRIPTION
            " This object indicates the number of droped bytes, which is lower 32 bits of the total number. "
        ::= { hwXQoSQppbPolicyStatisticsExtEntry 15 }

    hwXQoSQppbPolicyDropedBytesHigh OBJECT-TYPE
        SYNTAX  Unsigned32
        MAX-ACCESS read-only
        STATUS current
        DESCRIPTION
            " This object indicates the number of droped bytes, which is upper 32 bits of the total number. "
        ::= { hwXQoSQppbPolicyStatisticsExtEntry 16 }

    hwXQoSQppbPolicyMatchPacketsRateLow OBJECT-TYPE
        SYNTAX  Unsigned32
        MAX-ACCESS read-only
        STATUS current
        DESCRIPTION
            "This object indicates the rate of packets matching the QPPB policy, which is lower 32 bits of the total number. "
        ::= { hwXQoSQppbPolicyStatisticsExtEntry 17 }

    hwXQoSQppbPolicyMatchPacketsRateHigh OBJECT-TYPE
        SYNTAX  Unsigned32
        MAX-ACCESS read-only
        STATUS current
        DESCRIPTION
            "This object indicates the rate of packets matching the QPPB policy, which is upper 32 bits of the total number. "
        ::= { hwXQoSQppbPolicyStatisticsExtEntry 18 }

    hwXQoSQppbPolicyMatchBytesRateLow OBJECT-TYPE
        SYNTAX  Unsigned32
        MAX-ACCESS read-only
        STATUS current
        DESCRIPTION
            " This object indicates the rate of matched bytes, which is lower 32 bits of the total number. "
        ::= { hwXQoSQppbPolicyStatisticsExtEntry 19 }

    hwXQoSQppbPolicyMatchBytesRateHigh OBJECT-TYPE
        SYNTAX  Unsigned32
        MAX-ACCESS read-only
        STATUS current
        DESCRIPTION
            " This object indicates the rate of matched bytes, which is upper 32 bits of the total number. "
        ::= { hwXQoSQppbPolicyStatisticsExtEntry 20 }

    hwXQoSQppbGlobalStatisticsExtTable OBJECT-TYPE
        SYNTAX      SEQUENCE OF HwXQoSQppbGlobalStatisticsExtEntry
        MAX-ACCESS  not-accessible
        STATUS      current
        DESCRIPTION
            "This table displays global QPPB statistics. "
        ::= { hwXQoSBaObjects 46 }

    hwXQoSQppbGlobalStatisticsExtEntry OBJECT-TYPE
        SYNTAX HwXQoSQppbGlobalStatisticsExtEntry
        MAX-ACCESS not-accessible
        STATUS current
        DESCRIPTION
            "hwXQoSQppbGlobalStatisticsExtEntry"
        INDEX  { hwXQoSQppbGlobalStatisticsExtPolicyName,
                hwXQoSQppbGlobalStatisticsExtLocalID,
                hwXQoSQppbGlobalStatisticsExtDirection }
        ::= { hwXQoSQppbGlobalStatisticsExtTable 1 }

    HwXQoSQppbGlobalStatisticsExtEntry ::=
        SEQUENCE {
            hwXQoSQppbGlobalStatisticsExtPolicyName
                OCTET STRING,
            hwXQoSQppbGlobalStatisticsExtLocalID
                Integer32,
            hwXQoSQppbGlobalStatisticsExtDirection
                INTEGER,
            hwXQoSQppbGlobalStatisticsExtReset
                INTEGER,
            hwXQoSQppbGlobalStatisticsMatchedPacketsLow
                Unsigned32,
            hwXQoSQppbGlobalStatisticsMatchedPacketsHigh
                Unsigned32,
            hwXQoSQppbGlobalStatisticsMatchedBytesLow
                Unsigned32,
            hwXQoSQppbGlobalStatisticsMatchedBytesHigh
                Unsigned32,
            hwXQoSQppbGlobalStatisticsPassedPacketsLow
                Unsigned32,
            hwXQoSQppbGlobalStatisticsPassedPacketsHigh
                Unsigned32,
            hwXQoSQppbGlobalStatisticsPassedBytesLow
                Unsigned32,
            hwXQoSQppbGlobalStatisticsPassedBytesHigh
                Unsigned32,
            hwXQoSQppbGlobalStatisticsDropedPacketsLow
                Unsigned32,
            hwXQoSQppbGlobalStatisticsDropedPacketsHigh
                Unsigned32,
            hwXQoSQppbGlobalStatisticsDropedBytesLow
                Unsigned32,
            hwXQoSQppbGlobalStatisticsDropedBytesHigh
                Unsigned32,
            hwXQoSQppbGlobalStatisticsMatchPacketsRateLow
                Unsigned32,
            hwXQoSQppbGlobalStatisticsMatchPacketsRateHigh
                Unsigned32,
            hwXQoSQppbGlobalStatisticsMatchBytesRateLow
                Unsigned32,
            hwXQoSQppbGlobalStatisticsMatchBytesRateHigh
                Unsigned32
            }

    hwXQoSQppbGlobalStatisticsExtPolicyName  OBJECT-TYPE
        SYNTAX   OCTET STRING (SIZE (1..31))
        MAX-ACCESS read-only
        STATUS current
        DESCRIPTION
            " This object indicates the name of a QPPB policy. "
        ::= { hwXQoSQppbGlobalStatisticsExtEntry 1 }

    hwXQoSQppbGlobalStatisticsExtLocalID  OBJECT-TYPE
        SYNTAX Integer32
        MAX-ACCESS read-only
        STATUS current
        DESCRIPTION
            "This object indicates the qos-local-id ."
        ::= { hwXQoSQppbGlobalStatisticsExtEntry 2 }

    hwXQoSQppbGlobalStatisticsExtDirection  OBJECT-TYPE
        SYNTAX INTEGER
            {
            inbound(1),
            outbound(2)
            }
        MAX-ACCESS read-only
        STATUS current
        DESCRIPTION
            " This object indicates the traffic direction for which global QPPB statistics are queried.
                The value can be one of the following:
                inbound (1)
                outbound (2).  "
        ::= { hwXQoSQppbGlobalStatisticsExtEntry 3 }

    hwXQoSQppbGlobalStatisticsExtReset  OBJECT-TYPE
        SYNTAX INTEGER
        {
            reset(1)
        }
        MAX-ACCESS read-write
        STATUS current
        DESCRIPTION
            " This object indicates the statistics are reset.  "
        ::= { hwXQoSQppbGlobalStatisticsExtEntry 4 }

    hwXQoSQppbGlobalStatisticsMatchedPacketsLow OBJECT-TYPE
        SYNTAX  Unsigned32
        MAX-ACCESS read-only
        STATUS current
        DESCRIPTION
        " This object indicates the number of packets matching the QPPB policy, which is lower 32 bits of the total number. "
        ::= { hwXQoSQppbGlobalStatisticsExtEntry 5 }

    hwXQoSQppbGlobalStatisticsMatchedPacketsHigh OBJECT-TYPE
        SYNTAX  Unsigned32
        MAX-ACCESS read-only
        STATUS current
        DESCRIPTION
            " This object indicates the number of packets matching the QPPB policy, which is upper 32 bits of the total number. "
        ::= { hwXQoSQppbGlobalStatisticsExtEntry 6 }

    hwXQoSQppbGlobalStatisticsMatchedBytesLow OBJECT-TYPE
        SYNTAX  Unsigned32
        MAX-ACCESS read-only
        STATUS current
        DESCRIPTION
            " This object indicates the number of matched bytes, which is lower 32 bits of the total number. "
        ::= { hwXQoSQppbGlobalStatisticsExtEntry 7 }

    hwXQoSQppbGlobalStatisticsMatchedBytesHigh OBJECT-TYPE
        SYNTAX  Unsigned32
        MAX-ACCESS read-only
        STATUS current
        DESCRIPTION
            " This object indicates the number of matched bytes, which is upper 32 bits of the total number. "
        ::= { hwXQoSQppbGlobalStatisticsExtEntry 8 }

    hwXQoSQppbGlobalStatisticsPassedPacketsLow OBJECT-TYPE
        SYNTAX  Unsigned32
        MAX-ACCESS read-only
        STATUS current
        DESCRIPTION
            " hwXQoSQppbGlobalStatisticsPassedPackets, which is lower 32 bits of the total number."
        ::= { hwXQoSQppbGlobalStatisticsExtEntry 9 }

    hwXQoSQppbGlobalStatisticsPassedPacketsHigh OBJECT-TYPE
        SYNTAX  Unsigned32
        MAX-ACCESS read-only
        STATUS current
        DESCRIPTION
            " hwXQoSQppbGlobalStatisticsPassedPackets, which is upper 32 bits of the total number. "
        ::= { hwXQoSQppbGlobalStatisticsExtEntry 10 }

    hwXQoSQppbGlobalStatisticsPassedBytesLow OBJECT-TYPE
        SYNTAX  Unsigned32
        MAX-ACCESS read-only
        STATUS current
        DESCRIPTION
            " This object indicates the number of passed bytes, which is lower 32 bits of the total number. "
        ::= { hwXQoSQppbGlobalStatisticsExtEntry 11 }

    hwXQoSQppbGlobalStatisticsPassedBytesHigh OBJECT-TYPE
        SYNTAX  Unsigned32
        MAX-ACCESS read-only
        STATUS current
        DESCRIPTION
            " This object indicates the number of passed bytes, which is upper 32 bits of the total number. "
        ::= { hwXQoSQppbGlobalStatisticsExtEntry 12 }

    hwXQoSQppbGlobalStatisticsDropedPacketsLow OBJECT-TYPE
        SYNTAX  Unsigned32
        MAX-ACCESS read-only
        STATUS current
        DESCRIPTION
            " This object indicates the number of discarded packets, which is lower 32 bits of the total number. "
        ::= { hwXQoSQppbGlobalStatisticsExtEntry 13 }

    hwXQoSQppbGlobalStatisticsDropedPacketsHigh OBJECT-TYPE
        SYNTAX  Unsigned32
        MAX-ACCESS read-only
        STATUS current
        DESCRIPTION
            " This object indicates the number of discarded packets, which is upper 32 bits of the total number. "
        ::= { hwXQoSQppbGlobalStatisticsExtEntry 14 }

    hwXQoSQppbGlobalStatisticsDropedBytesLow OBJECT-TYPE
        SYNTAX  Unsigned32
        MAX-ACCESS read-only
        STATUS current
        DESCRIPTION
            " This object indicates the number of droped bytes, which is lower 32 bits of the total number. "
        ::= { hwXQoSQppbGlobalStatisticsExtEntry 15 }

    hwXQoSQppbGlobalStatisticsDropedBytesHigh OBJECT-TYPE
        SYNTAX  Unsigned32
        MAX-ACCESS read-only
        STATUS current
        DESCRIPTION
            " This object indicates the number of droped bytes, which is upper 32 bits of the total number. "
        ::= { hwXQoSQppbGlobalStatisticsExtEntry 16 }

    hwXQoSQppbGlobalStatisticsMatchPacketsRateLow OBJECT-TYPE
        SYNTAX  Unsigned32
        MAX-ACCESS read-only
        STATUS current
        DESCRIPTION
        " This object indicates the rate of packets matching the QPPB policy, which is lower 32 bits of the total number. "
        ::= { hwXQoSQppbGlobalStatisticsExtEntry 17 }

    hwXQoSQppbGlobalStatisticsMatchPacketsRateHigh OBJECT-TYPE
        SYNTAX  Unsigned32
        MAX-ACCESS read-only
        STATUS current
        DESCRIPTION
            " This object indicates the rate of packets matching the QPPB policy, which is upper 32 bits of the total number. "
        ::= { hwXQoSQppbGlobalStatisticsExtEntry 18 }

    hwXQoSQppbGlobalStatisticsMatchBytesRateLow OBJECT-TYPE
        SYNTAX  Unsigned32
        MAX-ACCESS read-only
        STATUS current
        DESCRIPTION
            " This object indicates the rate of matched bytes, which is lower 32 bits of the total number. "
        ::= { hwXQoSQppbGlobalStatisticsExtEntry 19 }

    hwXQoSQppbGlobalStatisticsMatchBytesRateHigh OBJECT-TYPE
        SYNTAX  Unsigned32
        MAX-ACCESS read-only
        STATUS current
        DESCRIPTION
            " This object indicates the rate of matched bytes, which is upper 32 bits of the total number. "
        ::= { hwXQoSQppbGlobalStatisticsExtEntry 20 }

-- ******************************************************************
--
--   hwXQoSCarStatisticsExtTable
--
-- ******************************************************************

    hwXQoSCarStatisticsExtTable OBJECT-TYPE
        SYNTAX      SEQUENCE OF HwXQoSCarStatisticsExtEntry
        MAX-ACCESS  not-accessible
        STATUS      current
        DESCRIPTION
            "This table displays CAR statistics on an interface. "
        ::= { hwXQoSBaObjects 47 }


    hwXQoSCarStatisticsExtEntry OBJECT-TYPE
        SYNTAX HwXQoSCarStatisticsExtEntry
        MAX-ACCESS not-accessible
        STATUS current
        DESCRIPTION
            " This table is used to query the CAR statistics on an interface. "
        INDEX  { hwXQoSCarStatisticsExtInterfaceIndex,hwXQoSCarStatisticsExtDirection,hwXQoSCarStatisticsExtVlanid,hwXQoSCarStatisticsExtSlotNumber}
        ::= { hwXQoSCarStatisticsExtTable 1 }

    HwXQoSCarStatisticsExtEntry ::=
        SEQUENCE {
            hwXQoSCarStatisticsExtInterfaceIndex
                InterfaceIndex,
            hwXQoSCarStatisticsExtDirection
                INTEGER,
            hwXQoSCarStatisticsExtVlanid
                Integer32,
            hwXQoSCarStatisticsExtSlotNumber
                Integer32,
            hwXQoSCarStatisticsExtReset
                INTEGER,
            hwXQoSCarStatisticsExtPassPacketsLow
                Unsigned32,
            hwXQoSCarStatisticsExtPassPacketsHigh
                Unsigned32,
            hwXQoSCarStatisticsExtPassBytesLow
                Unsigned32,
            hwXQoSCarStatisticsExtPassBytesHigh
                Unsigned32,
            hwXQoSCarStatisticsExtDropPacketsLow
                Unsigned32,
            hwXQoSCarStatisticsExtDropPacketsHigh
                Unsigned32,
            hwXQoSCarStatisticsExtDropBytesLow
                Unsigned32,
            hwXQoSCarStatisticsExtDropBytesHigh
                Unsigned32,
            hwXQoSCarStatisticsExtPassPacketsRateLow
                Unsigned32,
            hwXQoSCarStatisticsExtPassPacketsRateHigh
                Unsigned32,
            hwXQoSCarStatisticsExtPassBytesRateLow
                Unsigned32,
            hwXQoSCarStatisticsExtPassBytesRateHigh
                Unsigned32,
            hwXQoSCarStatisticsExtDropPacketsRateLow
                Unsigned32,
            hwXQoSCarStatisticsExtDropPacketsRateHigh
                Unsigned32,
            hwXQoSCarStatisticsExtDropBytesRateLow
                Unsigned32,
            hwXQoSCarStatisticsExtDropBytesRateHigh
                Unsigned32
    }

    hwXQoSCarStatisticsExtInterfaceIndex OBJECT-TYPE
        SYNTAX InterfaceIndex
        MAX-ACCESS read-only
        STATUS current
        DESCRIPTION
            " This object indicates the interface index."
        ::= { hwXQoSCarStatisticsExtEntry 1 }

    hwXQoSCarStatisticsExtDirection OBJECT-TYPE
        SYNTAX INTEGER
        {
            inbound(1),
            outbound(2)
        }
        MAX-ACCESS read-only
        STATUS current
        DESCRIPTION
            "This object indicates the traffic direction to which CAR applies.
        The value can be one of the following:
        inbound(1)
        outbound(2).
        "
        ::= { hwXQoSCarStatisticsExtEntry 2 }

    hwXQoSCarStatisticsExtVlanid OBJECT-TYPE
        SYNTAX Integer32 (0..4094)
        MAX-ACCESS read-only
        STATUS current
        DESCRIPTION
            " The value of this object identifies the VLAN ID of an interface where the CAR statistics are queried.
        The value ranges from 1 to 4094."
        ::= { hwXQoSCarStatisticsExtEntry 3 }

    hwXQoSCarStatisticsExtSlotNumber OBJECT-TYPE
        SYNTAX Integer32 (0..128)
        MAX-ACCESS read-only
        STATUS current
        DESCRIPTION
            " This object indicates the ID of the board where CAR statistics are queried.
        The value ranges from 0 to 128."
        ::= { hwXQoSCarStatisticsExtEntry 4 }

    hwXQoSCarStatisticsExtReset OBJECT-TYPE
        SYNTAX INTEGER
        {
            reset(1)
        }
        MAX-ACCESS read-create
        STATUS current
        DESCRIPTION
            " This object indicates the resetting of statistics."
        ::= { hwXQoSCarStatisticsExtEntry 5 }

    hwXQoSCarStatisticsExtPassPacketsLow OBJECT-TYPE
        SYNTAX  Unsigned32
        MAX-ACCESS read-only
        STATUS current
        DESCRIPTION
            " This object indicates the number of forwarded packets, which is lower 32 bits of the total number."
        ::= { hwXQoSCarStatisticsExtEntry 6 }

    hwXQoSCarStatisticsExtPassPacketsHigh OBJECT-TYPE
        SYNTAX  Unsigned32
        MAX-ACCESS read-only
        STATUS current
        DESCRIPTION
            " This object indicates the number of forwarded packets, which is upper 32 bits of the total number."
        ::= { hwXQoSCarStatisticsExtEntry 7 }

    hwXQoSCarStatisticsExtPassBytesLow OBJECT-TYPE
        SYNTAX  Unsigned32
        MAX-ACCESS read-only
        STATUS current
        DESCRIPTION
            " This object indicates the number of passed bytes, which is lower 32 bits of the total number."
        ::= { hwXQoSCarStatisticsExtEntry 8 }

    hwXQoSCarStatisticsExtPassBytesHigh OBJECT-TYPE
        SYNTAX  Unsigned32
        MAX-ACCESS read-only
        STATUS current
        DESCRIPTION
            " This object indicates the number of passed bytes, which is upper 32 bits of the total number."
        ::= { hwXQoSCarStatisticsExtEntry 9 }

    hwXQoSCarStatisticsExtDropPacketsLow OBJECT-TYPE
        SYNTAX  Unsigned32
        MAX-ACCESS read-only
        STATUS current
        DESCRIPTION
            " This object indicates the number of discarded packets, which is lower 32 bits of the total number."
        ::= { hwXQoSCarStatisticsExtEntry 10 }

    hwXQoSCarStatisticsExtDropPacketsHigh OBJECT-TYPE
        SYNTAX  Unsigned32
        MAX-ACCESS read-only
        STATUS current
        DESCRIPTION
            " This object indicates the number of discarded packets, which is upper 32 bits of the total number."
        ::= { hwXQoSCarStatisticsExtEntry 11 }

    hwXQoSCarStatisticsExtDropBytesLow OBJECT-TYPE
        SYNTAX  Unsigned32
        MAX-ACCESS read-only
        STATUS current
        DESCRIPTION
            " This object indicates the number of discarded bytes, which is lower 32 bits of the total number."
        ::= { hwXQoSCarStatisticsExtEntry 12 }

    hwXQoSCarStatisticsExtDropBytesHigh OBJECT-TYPE
        SYNTAX  Unsigned32
        MAX-ACCESS read-only
        STATUS current
        DESCRIPTION
            " This object indicates the number of discarded bytes, which is upper 32 bits of the total number."
        ::= { hwXQoSCarStatisticsExtEntry 13 }

    hwXQoSCarStatisticsExtPassPacketsRateLow OBJECT-TYPE
        SYNTAX  Unsigned32
        MAX-ACCESS read-only
        STATUS current
        DESCRIPTION
            " This object indicates the rate at which packets are forwarded, which is lower 32 bits of the total number."
        ::= { hwXQoSCarStatisticsExtEntry 14 }

    hwXQoSCarStatisticsExtPassPacketsRateHigh OBJECT-TYPE
        SYNTAX  Unsigned32
        MAX-ACCESS read-only
        STATUS current
        DESCRIPTION
            " This object indicates the rate at which packets are forwarded, which is upper 32 bits of the total number."
        ::= { hwXQoSCarStatisticsExtEntry 15 }

    hwXQoSCarStatisticsExtPassBytesRateLow  OBJECT-TYPE
        SYNTAX  Unsigned32
        MAX-ACCESS read-only
        STATUS current
        DESCRIPTION
            " This object indicates the byte pass rate, which is lower 32 bits of the total number."
        ::= { hwXQoSCarStatisticsExtEntry 16 }

    hwXQoSCarStatisticsExtPassBytesRateHigh  OBJECT-TYPE
        SYNTAX  Unsigned32
        MAX-ACCESS read-only
        STATUS current
        DESCRIPTION
            " This object indicates the byte pass rate, which is upper 32 bits of the total number."
        ::= { hwXQoSCarStatisticsExtEntry 17 }

    hwXQoSCarStatisticsExtDropPacketsRateLow OBJECT-TYPE
        SYNTAX  Unsigned32
        MAX-ACCESS read-only
        STATUS current
        DESCRIPTION
            " This object indicates the rate at which packets are discarded, which is lower 32 bits of the total number."
        ::= { hwXQoSCarStatisticsExtEntry 18 }

    hwXQoSCarStatisticsExtDropPacketsRateHigh OBJECT-TYPE
        SYNTAX  Unsigned32
        MAX-ACCESS read-only
        STATUS current
        DESCRIPTION
            " This object indicates the rate at which packets are discarded, which is upper 32 bits of the total number."
        ::= { hwXQoSCarStatisticsExtEntry 19 }

    hwXQoSCarStatisticsExtDropBytesRateLow  OBJECT-TYPE
        SYNTAX  Unsigned32
        MAX-ACCESS read-only
        STATUS current
        DESCRIPTION
            " This object indicates the byte drop rate, which is lower 32 bits of the total number."
        ::= { hwXQoSCarStatisticsExtEntry 20 }

    hwXQoSCarStatisticsExtDropBytesRateHigh  OBJECT-TYPE
        SYNTAX  Unsigned32
        MAX-ACCESS read-only
        STATUS current
        DESCRIPTION
            " This object indicates the byte drop rate, which is upper 32 bits of the total number."
        ::= { hwXQoSCarStatisticsExtEntry 21 }

--********************************************************************
--   hwXQoSPortQueueStatisticsExtTable
--
-- ******************************************************************

    hwXQoSPortQueueStatisticsExtTable OBJECT-TYPE
        SYNTAX      SEQUENCE OF HwXQoSPortQueueStatisticsExtEntry
        MAX-ACCESS  not-accessible
        STATUS      current
        DESCRIPTION
            " This table is used to query the statistics of class queues. "
        ::= { hwXQoSBaObjects 48 }

    hwXQoSPortQueueStatisticsExtEntry OBJECT-TYPE
        SYNTAX HwXQoSPortQueueStatisticsExtEntry
        MAX-ACCESS not-accessible
        STATUS current
        DESCRIPTION
            " This table is used to query the statistics of class queues. "
        INDEX { hwXQoSPortQueueStatisticsExtInterfaceIndex,
                hwXQoSPortQueueStatisticsExtDirection,
                hwXQoSPortQueueStatisticsExtQueueIndex }
        ::= { hwXQoSPortQueueStatisticsExtTable 1 }

    HwXQoSPortQueueStatisticsExtEntry ::=
        SEQUENCE {
            hwXQoSPortQueueStatisticsExtInterfaceIndex
                InterfaceIndex,
            hwXQoSPortQueueStatisticsExtDirection
                INTEGER,
            hwXQoSPortQueueStatisticsExtQueueIndex
                INTEGER,
            hwXQoSPortQueueStatisticsExtReset
                INTEGER,
            hwXQoSPortQueueStatisticsExtTotalPassPacketsLow
                Unsigned32,
            hwXQoSPortQueueStatisticsExtTotalPassPacketsHigh
                Unsigned32,
            hwXQoSPortQueueStatisticsExtTotalPassBytesLow
                Unsigned32,
            hwXQoSPortQueueStatisticsExtTotalPassBytesHigh
                Unsigned32,
            hwXQoSPortQueueStatisticsExtTotalDiscardPacketsLow
                Unsigned32,
            hwXQoSPortQueueStatisticsExtTotalDiscardPacketsHigh
                Unsigned32,
            hwXQoSPortQueueStatisticsExtTotalDiscardBytesLow
                Unsigned32,
            hwXQoSPortQueueStatisticsExtTotalDiscardBytesHigh
                Unsigned32,
            hwXQoSPortQueueStatisticsExtDropTailDiscardPacketsLow
                Unsigned32,
            hwXQoSPortQueueStatisticsExtDropTailDiscardPacketsHigh
                Unsigned32,
            hwXQoSPortQueueStatisticsExtDropTailDiscardBytesLow
                Unsigned32,
            hwXQoSPortQueueStatisticsExtDropTailDiscardBytesHigh
                Unsigned32,
            hwXQoSPortQueueStatisticsExtWredDiscardPacketsLow
                Unsigned32,
            hwXQoSPortQueueStatisticsExtWredDiscardPacketsHigh
                Unsigned32,
            hwXQoSPortQueueStatisticsExtWredDiscardBytesLow
                Unsigned32,
            hwXQoSPortQueueStatisticsExtWredDiscardBytesHigh
                Unsigned32,
            hwXQoSPortQueueStatisticsExtPassPacketsRateLow
                Unsigned32,
            hwXQoSPortQueueStatisticsExtPassPacketsRateHigh
                Unsigned32,
            hwXQoSPortQueueStatisticsExtPassBytesRateLow
                Unsigned32,
            hwXQoSPortQueueStatisticsExtPassBytesRateHigh
                Unsigned32,
            hwXQoSPortQueueStatisticsExtDiscardPacketsRateLow
                Unsigned32,
            hwXQoSPortQueueStatisticsExtDiscardPacketsRateHigh
                Unsigned32,
            hwXQoSPortQueueStatisticsExtDiscardBytesRateLow
                Unsigned32,
            hwXQoSPortQueueStatisticsExtDiscardBytesRateHigh
                Unsigned32,
            hwXQoSPortQueueStatisticsExtDropTailDiscardPacketsRateLow
                Unsigned32,
            hwXQoSPortQueueStatisticsExtDropTailDiscardPacketsRateHigh
                Unsigned32,
            hwXQoSPortQueueStatisticsExtDropTailDiscardBytesRateLow
                Unsigned32,
            hwXQoSPortQueueStatisticsExtDropTailDiscardBytesRateHigh
                Unsigned32,
            hwXQoSPortQueueStatisticsExtWredDiscardPacketsRateLow
                Unsigned32,
            hwXQoSPortQueueStatisticsExtWredDiscardPacketsRateHigh
                Unsigned32,
            hwXQoSPortQueueStatisticsExtWredDiscardBytesRateLow
                Unsigned32,
            hwXQoSPortQueueStatisticsExtWredDiscardBytesRateHigh
                Unsigned32,
            hwXQoSPortQueueStatisticsExtTrafficTowardThisPortLow
                Unsigned32,
            hwXQoSPortQueueStatisticsExtTrafficTowardThisPortHigh
                Unsigned32,
            hwXQoSPortQueueStatisticsExtPhysicalBandwidthOfPortQoSLow
                Unsigned32,
            hwXQoSPortQueueStatisticsExtPhysicalBandwidthOfPortQoSHigh
                Unsigned32,
            hwXQoSPortQueueStatisticsExtQueuePercentage
                Integer32,
            hwXQoSPortQueueStatisticsExtTotalPacketsLow
                Unsigned32,
            hwXQoSPortQueueStatisticsExtTotalPacketsHigh
                Unsigned32,
            hwXQoSPortQueueStatisticsExtTotalBytesLow
                Unsigned32,
            hwXQoSPortQueueStatisticsExtTotalBytesHigh
                Unsigned32
                }

    hwXQoSPortQueueStatisticsExtInterfaceIndex  OBJECT-TYPE
        SYNTAX   InterfaceIndex
        MAX-ACCESS read-only
        STATUS current
        DESCRIPTION
            " This object indicates the interface index. "
        ::= { hwXQoSPortQueueStatisticsExtEntry 1 }

    hwXQoSPortQueueStatisticsExtDirection  OBJECT-TYPE
        SYNTAX INTEGER
            {
            inbound(1),
            outbound(2)
            }
        MAX-ACCESS read-only
        STATUS current
        DESCRIPTION
        " This object indicates the traffic direction whose statistics are queried.
            The value can be one of the following:
            inbound(1)
            outbound(2)."
        ::= { hwXQoSPortQueueStatisticsExtEntry 2 }

    hwXQoSPortQueueStatisticsExtQueueIndex  OBJECT-TYPE
        SYNTAX INTEGER
            {
                be(1),
                af1(2),
                af2(3),
                af3(4),
                af4(5),
                ef(6),
                cs6(7),
                cs7(8),
                total(9)
            }
        MAX-ACCESS read-only
        STATUS current
        DESCRIPTION
            " This object indicates the priority of a class queue where statistics are queried.
            The value can be:
            1 be
            2 af1
            3 af2
            4 af3
            5 af4
            6 ef
            7 cs6
            8 cs7
            9 total
            "
        ::= { hwXQoSPortQueueStatisticsExtEntry 3 }


      hwXQoSPortQueueStatisticsExtReset  OBJECT-TYPE
         SYNTAX INTEGER
        {
            reset(1)
        }
        MAX-ACCESS read-create
        STATUS current
        DESCRIPTION
            " This object indicates the flag of clearing the statistics.  "
        ::= { hwXQoSPortQueueStatisticsExtEntry 4 }

    hwXQoSPortQueueStatisticsExtTotalPassPacketsLow OBJECT-TYPE
        SYNTAX  Unsigned32
        MAX-ACCESS read-only
        STATUS current
        DESCRIPTION
            " This object indicates the number of passed packets. "
        ::= { hwXQoSPortQueueStatisticsExtEntry 5 }

    hwXQoSPortQueueStatisticsExtTotalPassPacketsHigh OBJECT-TYPE
        SYNTAX  Unsigned32
        MAX-ACCESS read-only
        STATUS current
        DESCRIPTION
            " This object indicates the number of passed packets. "
        ::= { hwXQoSPortQueueStatisticsExtEntry 6 }


    hwXQoSPortQueueStatisticsExtTotalPassBytesLow OBJECT-TYPE
        SYNTAX  Unsigned32
        MAX-ACCESS read-only
        STATUS current
        DESCRIPTION
            " This object indicates the number of forwarded bytes. "
        ::= { hwXQoSPortQueueStatisticsExtEntry 7 }

    hwXQoSPortQueueStatisticsExtTotalPassBytesHigh OBJECT-TYPE
        SYNTAX  Unsigned32
        MAX-ACCESS read-only
        STATUS current
        DESCRIPTION
            " This object indicates the number of forwarded bytes. "
        ::= { hwXQoSPortQueueStatisticsExtEntry 8 }

    hwXQoSPortQueueStatisticsExtTotalDiscardPacketsLow OBJECT-TYPE
        SYNTAX  Unsigned32
        MAX-ACCESS read-only
        STATUS current
        DESCRIPTION
            " This object indicates the number of discarded packets. "
        ::= { hwXQoSPortQueueStatisticsExtEntry 9 }

    hwXQoSPortQueueStatisticsExtTotalDiscardPacketsHigh OBJECT-TYPE
        SYNTAX  Unsigned32
        MAX-ACCESS read-only
        STATUS current
        DESCRIPTION
            " This object indicates the number of discarded packets. "
        ::= { hwXQoSPortQueueStatisticsExtEntry 10 }

    hwXQoSPortQueueStatisticsExtTotalDiscardBytesLow OBJECT-TYPE
        SYNTAX  Unsigned32
        MAX-ACCESS read-only
        STATUS current
        DESCRIPTION
            " This object indicates the number of dropped bytes. "
        ::= { hwXQoSPortQueueStatisticsExtEntry 11 }

    hwXQoSPortQueueStatisticsExtTotalDiscardBytesHigh OBJECT-TYPE
        SYNTAX  Unsigned32
        MAX-ACCESS read-only
        STATUS current
        DESCRIPTION
            " This object indicates the number of dropped bytes. "
        ::= { hwXQoSPortQueueStatisticsExtEntry 12 }

    hwXQoSPortQueueStatisticsExtDropTailDiscardPacketsLow OBJECT-TYPE
        SYNTAX  Unsigned32
        MAX-ACCESS read-only
        STATUS current
        DESCRIPTION
            " The value of this object identifies the number of discarded tail packets. "
        ::= { hwXQoSPortQueueStatisticsExtEntry 13 }

    hwXQoSPortQueueStatisticsExtDropTailDiscardPacketsHigh OBJECT-TYPE
        SYNTAX  Unsigned32
        MAX-ACCESS read-only
        STATUS current
        DESCRIPTION
            " The value of this object identifies the number of discarded tail packets. "
        ::= { hwXQoSPortQueueStatisticsExtEntry 14 }

    hwXQoSPortQueueStatisticsExtDropTailDiscardBytesLow OBJECT-TYPE
        SYNTAX  Unsigned32
        MAX-ACCESS read-only
        STATUS current
        DESCRIPTION
            "This object indicates the number of bytes discarded by tail drop. "
        ::= { hwXQoSPortQueueStatisticsExtEntry 15 }

    hwXQoSPortQueueStatisticsExtDropTailDiscardBytesHigh OBJECT-TYPE
        SYNTAX  Unsigned32
        MAX-ACCESS read-only
        STATUS current
        DESCRIPTION
            "This object indicates the number of bytes discarded by tail drop. "
        ::= { hwXQoSPortQueueStatisticsExtEntry 16 }

    hwXQoSPortQueueStatisticsExtWredDiscardPacketsLow OBJECT-TYPE
        SYNTAX  Unsigned32
        MAX-ACCESS read-only
        STATUS current
        DESCRIPTION
            " The value of this object identifies the number of packets that are discarded by WRED. "
        ::= { hwXQoSPortQueueStatisticsExtEntry 17 }

    hwXQoSPortQueueStatisticsExtWredDiscardPacketsHigh OBJECT-TYPE
        SYNTAX  Unsigned32
        MAX-ACCESS read-only
        STATUS current
        DESCRIPTION
            " The value of this object identifies the number of packets that are discarded by WRED. "
        ::= { hwXQoSPortQueueStatisticsExtEntry 18 }

    hwXQoSPortQueueStatisticsExtWredDiscardBytesLow OBJECT-TYPE
        SYNTAX  Unsigned32
        MAX-ACCESS read-only
        STATUS current
        DESCRIPTION
            "This object indicates the number of bytes discarded by WRED. "
        ::= { hwXQoSPortQueueStatisticsExtEntry 19 }

    hwXQoSPortQueueStatisticsExtWredDiscardBytesHigh OBJECT-TYPE
        SYNTAX  Unsigned32
        MAX-ACCESS read-only
        STATUS current
        DESCRIPTION
            "This object indicates the number of bytes discarded by WRED. "
        ::= { hwXQoSPortQueueStatisticsExtEntry 20 }

    hwXQoSPortQueueStatisticsExtPassPacketsRateLow OBJECT-TYPE
        SYNTAX  Unsigned32
        MAX-ACCESS read-only
        STATUS current
        DESCRIPTION
            " This object indicates the packet pass rate. "
        ::= { hwXQoSPortQueueStatisticsExtEntry 21 }

    hwXQoSPortQueueStatisticsExtPassPacketsRateHigh OBJECT-TYPE
        SYNTAX  Unsigned32
        MAX-ACCESS read-only
        STATUS current
        DESCRIPTION
            " This object indicates the packet pass rate. "
        ::= { hwXQoSPortQueueStatisticsExtEntry 22 }

    hwXQoSPortQueueStatisticsExtPassBytesRateLow OBJECT-TYPE
        SYNTAX  Unsigned32
        MAX-ACCESS read-only
        STATUS current
        DESCRIPTION
            " This object indicates the rate at which bytes are forwarded. "
        ::= { hwXQoSPortQueueStatisticsExtEntry 23 }

    hwXQoSPortQueueStatisticsExtPassBytesRateHigh OBJECT-TYPE
        SYNTAX  Unsigned32
        MAX-ACCESS read-only
        STATUS current
        DESCRIPTION
            " This object indicates the rate at which bytes are forwarded. "
        ::= { hwXQoSPortQueueStatisticsExtEntry 24 }

    hwXQoSPortQueueStatisticsExtDiscardPacketsRateLow OBJECT-TYPE
        SYNTAX  Unsigned32
        MAX-ACCESS read-only
        STATUS current
        DESCRIPTION
            " This object indicates the packet drop rate. "
        ::= { hwXQoSPortQueueStatisticsExtEntry 25 }

    hwXQoSPortQueueStatisticsExtDiscardPacketsRateHigh OBJECT-TYPE
        SYNTAX  Unsigned32
        MAX-ACCESS read-only
        STATUS current
        DESCRIPTION
            " This object indicates the packet drop rate. "
        ::= { hwXQoSPortQueueStatisticsExtEntry 26 }

    hwXQoSPortQueueStatisticsExtDiscardBytesRateLow OBJECT-TYPE
        SYNTAX  Unsigned32
        MAX-ACCESS read-only
        STATUS current
        DESCRIPTION
            " This object indicates the rate at which bytes are discarded. "
        ::= { hwXQoSPortQueueStatisticsExtEntry 27 }

    hwXQoSPortQueueStatisticsExtDiscardBytesRateHigh OBJECT-TYPE
        SYNTAX  Unsigned32
        MAX-ACCESS read-only
        STATUS current
        DESCRIPTION
            " This object indicates the rate at which bytes are discarded. "
        ::= { hwXQoSPortQueueStatisticsExtEntry 28 }


    hwXQoSPortQueueStatisticsExtDropTailDiscardPacketsRateLow OBJECT-TYPE
        SYNTAX  Unsigned32
        MAX-ACCESS read-only
        STATUS current
        DESCRIPTION
            " This object indicates the tail packet discarding rate. "
        ::= { hwXQoSPortQueueStatisticsExtEntry 29 }

    hwXQoSPortQueueStatisticsExtDropTailDiscardPacketsRateHigh OBJECT-TYPE
        SYNTAX  Unsigned32
        MAX-ACCESS read-only
        STATUS current
        DESCRIPTION
            " This object indicates the tail packet discarding rate. "
        ::= { hwXQoSPortQueueStatisticsExtEntry 30 }

    hwXQoSPortQueueStatisticsExtDropTailDiscardBytesRateLow OBJECT-TYPE
        SYNTAX  Unsigned32
        MAX-ACCESS read-only
        STATUS current
        DESCRIPTION
            " This object indicates the rate at which bytes are discarded by tail drop. "
        ::= { hwXQoSPortQueueStatisticsExtEntry 31 }

    hwXQoSPortQueueStatisticsExtDropTailDiscardBytesRateHigh OBJECT-TYPE
        SYNTAX  Unsigned32
        MAX-ACCESS read-only
        STATUS current
        DESCRIPTION
            " This object indicates the rate at which bytes are discarded by tail drop. "
        ::= { hwXQoSPortQueueStatisticsExtEntry 32 }

    hwXQoSPortQueueStatisticsExtWredDiscardPacketsRateLow OBJECT-TYPE
        SYNTAX  Unsigned32
        MAX-ACCESS read-only
        STATUS current
        DESCRIPTION
            " This object indicates the WRED packet discarding rate."
        ::= { hwXQoSPortQueueStatisticsExtEntry 33 }

    hwXQoSPortQueueStatisticsExtWredDiscardPacketsRateHigh OBJECT-TYPE
        SYNTAX  Unsigned32
        MAX-ACCESS read-only
        STATUS current
        DESCRIPTION
            " This object indicates the WRED packet discarding rate."
        ::= { hwXQoSPortQueueStatisticsExtEntry 34 }


    hwXQoSPortQueueStatisticsExtWredDiscardBytesRateLow OBJECT-TYPE
        SYNTAX  Unsigned32
        MAX-ACCESS read-only
        STATUS current
        DESCRIPTION
            " This object indicates the WRED byte discarding rate."
        ::= { hwXQoSPortQueueStatisticsExtEntry 35 }

    hwXQoSPortQueueStatisticsExtWredDiscardBytesRateHigh OBJECT-TYPE
        SYNTAX  Unsigned32
        MAX-ACCESS read-only
        STATUS current
        DESCRIPTION
            " This object indicates the WRED byte discarding rate."
        ::= { hwXQoSPortQueueStatisticsExtEntry 36 }

    hwXQoSPortQueueStatisticsExtTrafficTowardThisPortLow OBJECT-TYPE
        SYNTAX  Unsigned32
        UNITS "bps"
        MAX-ACCESS read-only
        STATUS current
        DESCRIPTION
            " This object indicates the port traffic information."
        ::= { hwXQoSPortQueueStatisticsExtEntry 37 }

    hwXQoSPortQueueStatisticsExtTrafficTowardThisPortHigh OBJECT-TYPE
        SYNTAX  Unsigned32
        UNITS "bps"
        MAX-ACCESS read-only
        STATUS current
        DESCRIPTION
            " This object indicates the port traffic information."
        ::= { hwXQoSPortQueueStatisticsExtEntry 38 }


    hwXQoSPortQueueStatisticsExtPhysicalBandwidthOfPortQoSLow OBJECT-TYPE
        SYNTAX  Unsigned32
        UNITS "bps"
        MAX-ACCESS read-only
        STATUS current
        DESCRIPTION
            " This object indicates the physical bandwidth of a QoS interface."
        ::= { hwXQoSPortQueueStatisticsExtEntry 39 }

    hwXQoSPortQueueStatisticsExtPhysicalBandwidthOfPortQoSHigh OBJECT-TYPE
        SYNTAX  Unsigned32
        UNITS "bps"
        MAX-ACCESS read-only
        STATUS current
        DESCRIPTION
            " This object indicates the physical bandwidth of a QoS interface."
        ::= { hwXQoSPortQueueStatisticsExtEntry 40 }

    hwXQoSPortQueueStatisticsExtQueuePercentage OBJECT-TYPE
        SYNTAX Integer32 (0..100)
        MAX-ACCESS read-only
        STATUS current
        DESCRIPTION
            "This object indicates the percentage of the queue usage."
        ::= { hwXQoSPortQueueStatisticsExtEntry 41 }

    hwXQoSPortQueueStatisticsExtTotalPacketsLow OBJECT-TYPE
        SYNTAX  Unsigned32
        MAX-ACCESS read-only
        STATUS current
        DESCRIPTION
            " This object indicates the total number of packets."
        ::= { hwXQoSPortQueueStatisticsExtEntry 42 }
    hwXQoSPortQueueStatisticsExtTotalPacketsHigh OBJECT-TYPE
        SYNTAX  Unsigned32
        MAX-ACCESS read-only
        STATUS current
        DESCRIPTION
            " This object indicates the total number of packets."
        ::= { hwXQoSPortQueueStatisticsExtEntry 43 }
    hwXQoSPortQueueStatisticsExtTotalBytesLow OBJECT-TYPE
        SYNTAX  Unsigned32
        MAX-ACCESS read-only
        STATUS current
        DESCRIPTION
            " This object indicates the total number of bytes."
        ::= { hwXQoSPortQueueStatisticsExtEntry 44 }
    hwXQoSPortQueueStatisticsExtTotalBytesHigh OBJECT-TYPE
        SYNTAX  Unsigned32
        MAX-ACCESS read-only
        STATUS current
        DESCRIPTION
            " This object indicates the total number of bytes."
        ::= { hwXQoSPortQueueStatisticsExtEntry 45 }
--
--   hwXQoSHardPipeStatisticsExtTable
--
-- ******************************************************************

    hwXQoSHardPipeStatisticsExtTable OBJECT-TYPE
        SYNTAX      SEQUENCE OF HwXQoSHardPipeStatisticsExtEntry
        MAX-ACCESS  not-accessible
        STATUS      current
        DESCRIPTION
            " This table is used to display statistics about outgoing packets on the PW-side and AC-side hard pipe. "
        ::= { hwXQoSBaObjects 49 }

    hwXQoSHardPipeStatisticsExtEntry OBJECT-TYPE
        SYNTAX HwXQoSHardPipeStatisticsExtEntry
        MAX-ACCESS not-accessible
        STATUS current
        DESCRIPTION
            " This table is used to query the statistics of hard pipe statistics. "
        INDEX  { hwXQoSHardPipeStatisticsExtInterfaceIndex}
        ::= { hwXQoSHardPipeStatisticsExtTable 1 }

    HwXQoSHardPipeStatisticsExtEntry ::=
        SEQUENCE {
            hwXQoSHardPipeStatisticsExtInterfaceIndex
                InterfaceIndex,
            hwXQoSHardPipeStatisticsExtReset
                INTEGER,
            hwXQoSHardPipeStatisticsExtPassPacketsLow
                Unsigned32,
            hwXQoSHardPipeStatisticsExtPassPacketsHigh
                Unsigned32,
            hwXQoSHardPipeStatisticsExtPassBytesLow
                Unsigned32,
            hwXQoSHardPipeStatisticsExtPassBytesHigh
                Unsigned32,
            hwXQoSHardPipeStatisticsExtDiscardPacketsLow
                Unsigned32,
            hwXQoSHardPipeStatisticsExtDiscardPacketsHigh
                Unsigned32,
            hwXQoSHardPipeStatisticsExtDiscardBytesLow
                Unsigned32,
            hwXQoSHardPipeStatisticsExtDiscardBytesHigh
                Unsigned32,
            hwXQoSHardPipeStatisticsExtPassPacketsRateLow
                Unsigned32,
            hwXQoSHardPipeStatisticsExtPassPacketsRateHigh
                Unsigned32,
            hwXQoSHardPipeStatisticsExtPassBytesRateLow
                Unsigned32,
            hwXQoSHardPipeStatisticsExtPassBytesRateHigh
                Unsigned32,
            hwXQoSHardPipeStatisticsExtDiscardPacketsRateLow
                Unsigned32,
            hwXQoSHardPipeStatisticsExtDiscardPacketsRateHigh
                Unsigned32,
            hwXQoSHardPipeStatisticsExtDiscardBytesRateLow
                Unsigned32,
            hwXQoSHardPipeStatisticsExtDiscardBytesRateHigh
                Unsigned32
                }

    hwXQoSHardPipeStatisticsExtInterfaceIndex  OBJECT-TYPE
        SYNTAX   InterfaceIndex
        MAX-ACCESS read-only
        STATUS current
        DESCRIPTION
        " This object indicates the hard pipe interface. "
        ::= { hwXQoSHardPipeStatisticsExtEntry 1 }

    hwXQoSHardPipeStatisticsExtReset  OBJECT-TYPE
        SYNTAX INTEGER
        {
            reset(1)
        }
        MAX-ACCESS read-create
        STATUS current
        DESCRIPTION
            " This object indicates the flag of clearing hard pipe traffic statistics.  "
        ::= { hwXQoSHardPipeStatisticsExtEntry 2 }


    hwXQoSHardPipeStatisticsExtPassPacketsLow OBJECT-TYPE
        SYNTAX  Unsigned32
        MAX-ACCESS read-only
        STATUS current
        DESCRIPTION
            " This object indicates the number of packets forwarded by the hard pipe. "
        ::= { hwXQoSHardPipeStatisticsExtEntry 3 }

    hwXQoSHardPipeStatisticsExtPassPacketsHigh OBJECT-TYPE
        SYNTAX  Unsigned32
        MAX-ACCESS read-only
        STATUS current
        DESCRIPTION
            " This object indicates the number of packets forwarded by the hard pipe. "
        ::= { hwXQoSHardPipeStatisticsExtEntry 4 }


    hwXQoSHardPipeStatisticsExtPassBytesLow OBJECT-TYPE
        SYNTAX  Unsigned32
        MAX-ACCESS read-only
        STATUS current
        DESCRIPTION
            " This object indicates the number of  passed bytes. "
        ::= { hwXQoSHardPipeStatisticsExtEntry 5 }

    hwXQoSHardPipeStatisticsExtPassBytesHigh OBJECT-TYPE
        SYNTAX  Unsigned32
        MAX-ACCESS read-only
        STATUS current
        DESCRIPTION
            " This object indicates the number of  passed bytes. "
        ::= { hwXQoSHardPipeStatisticsExtEntry 6 }

    hwXQoSHardPipeStatisticsExtDiscardPacketsLow OBJECT-TYPE
        SYNTAX  Unsigned32
        MAX-ACCESS read-only
        STATUS current
        DESCRIPTION
            " This object indicates the number of packets discarded by the hard pipe."
        ::= { hwXQoSHardPipeStatisticsExtEntry 7 }

    hwXQoSHardPipeStatisticsExtDiscardPacketsHigh OBJECT-TYPE
        SYNTAX  Unsigned32
        MAX-ACCESS read-only
        STATUS current
            DESCRIPTION
            " This object indicates the number of packets discarded by the hard pipe."
        ::= { hwXQoSHardPipeStatisticsExtEntry 8 }

    hwXQoSHardPipeStatisticsExtDiscardBytesLow OBJECT-TYPE
        SYNTAX  Unsigned32
        MAX-ACCESS read-only
        STATUS current
        DESCRIPTION
            " This object indicates the number of discarded bytes. "
        ::= { hwXQoSHardPipeStatisticsExtEntry 9 }

    hwXQoSHardPipeStatisticsExtDiscardBytesHigh OBJECT-TYPE
            SYNTAX  Unsigned32
            MAX-ACCESS read-only
            STATUS current
        DESCRIPTION
            " This object indicates the number of discarded bytes. "
        ::= { hwXQoSHardPipeStatisticsExtEntry 10 }

    hwXQoSHardPipeStatisticsExtPassPacketsRateLow OBJECT-TYPE
        SYNTAX  Unsigned32
        MAX-ACCESS read-only
        STATUS current
        DESCRIPTION
            " This object indicates the rate at which the hard pipe forwards packets."
        ::= { hwXQoSHardPipeStatisticsExtEntry 11 }

    hwXQoSHardPipeStatisticsExtPassPacketsRateHigh OBJECT-TYPE
        SYNTAX  Unsigned32
        MAX-ACCESS read-only
        STATUS current
        DESCRIPTION
            " This object indicates the rate at which the hard pipe forwards packets."
        ::= { hwXQoSHardPipeStatisticsExtEntry 12 }

    hwXQoSHardPipeStatisticsExtPassBytesRateLow OBJECT-TYPE
        SYNTAX  Unsigned32
        MAX-ACCESS read-only
        STATUS current
        DESCRIPTION
            " The value of this object identifies the rate of pass bytes. "
        ::= { hwXQoSHardPipeStatisticsExtEntry 13 }

    hwXQoSHardPipeStatisticsExtPassBytesRateHigh OBJECT-TYPE
        SYNTAX  Unsigned32
        MAX-ACCESS read-only
        STATUS current
        DESCRIPTION
            " The value of this object identifies the rate of pass bytes. "
        ::= { hwXQoSHardPipeStatisticsExtEntry 14 }

    hwXQoSHardPipeStatisticsExtDiscardPacketsRateLow OBJECT-TYPE
        SYNTAX  Unsigned32
        MAX-ACCESS read-only
        STATUS current
        DESCRIPTION
            " This object indicates the rate at which the hard pipe discards packets."
        ::= { hwXQoSHardPipeStatisticsExtEntry 15 }

    hwXQoSHardPipeStatisticsExtDiscardPacketsRateHigh OBJECT-TYPE
        SYNTAX  Unsigned32
        MAX-ACCESS read-only
        STATUS current
        DESCRIPTION
            " This object indicates the rate at which the hard pipe discards packets."
        ::= { hwXQoSHardPipeStatisticsExtEntry 16 }

    hwXQoSHardPipeStatisticsExtDiscardBytesRateLow OBJECT-TYPE
        SYNTAX  Unsigned32
        MAX-ACCESS read-only
        STATUS current
        DESCRIPTION
            " The value of this object identifies the rate of discarded bytes."
        ::= { hwXQoSHardPipeStatisticsExtEntry 17 }

    hwXQoSHardPipeStatisticsExtDiscardBytesRateHigh OBJECT-TYPE
        SYNTAX  Unsigned32
        MAX-ACCESS read-only
        STATUS current
        DESCRIPTION
            " The value of this object identifies the rate of discarded bytes."
        ::= { hwXQoSHardPipeStatisticsExtEntry 18 }

--   hwXQoSHardPipeAccessStatisticsExtTable
--
-- ******************************************************************

    hwXQoSHardPipeAccessStatisticsExtTable OBJECT-TYPE
        SYNTAX      SEQUENCE OF HwXQoSHardPipeAccessStatisticsExtEntry
        MAX-ACCESS  not-accessible
        STATUS      current
        DESCRIPTION
            " This table is used to query the hard pipe statistics of access interface. "
        ::= { hwXQoSBaObjects 50 }


    hwXQoSHardPipeAccessStatisticsExtEntry OBJECT-TYPE
        SYNTAX HwXQoSHardPipeAccessStatisticsExtEntry
        MAX-ACCESS not-accessible
        STATUS current
        DESCRIPTION
            " This table is used to query the hard pipe statistics of access interface. "
        INDEX  { hwXQoSHardPipeAccessStatisticsExtInterfaceIndex,
                   hwXQoSHardPipeAccessStatisticsExtDirection }
        ::= { hwXQoSHardPipeAccessStatisticsExtTable 1 }

    HwXQoSHardPipeAccessStatisticsExtEntry ::=
        SEQUENCE {
            hwXQoSHardPipeAccessStatisticsExtInterfaceIndex
                InterfaceIndex,
            hwXQoSHardPipeAccessStatisticsExtDirection
                INTEGER,
            hwXQoSHardPipeAccessStatisticsExtReset
                INTEGER,
            hwXQoSHardPipeAccessStatisticsExtPassPacketsLow
                Unsigned32,
            hwXQoSHardPipeAccessStatisticsExtPassPacketsHigh
                Unsigned32,
            hwXQoSHardPipeAccessStatisticsExtPassBytesLow
                Unsigned32,
            hwXQoSHardPipeAccessStatisticsExtPassBytesHigh
                Unsigned32,
            hwXQoSHardPipeAccessStatisticsExtDiscardPacketsLow
                Unsigned32,
            hwXQoSHardPipeAccessStatisticsExtDiscardPacketsHigh
                Unsigned32,
            hwXQoSHardPipeAccessStatisticsExtDiscardBytesLow
                Unsigned32,
            hwXQoSHardPipeAccessStatisticsExtDiscardBytesHigh
                Unsigned32,
            hwXQoSHardPipeAccessStatisticsExtPassPacketsRateLow
                Unsigned32,
            hwXQoSHardPipeAccessStatisticsExtPassPacketsRateHigh
                Unsigned32,
            hwXQoSHardPipeAccessStatisticsExtPassBytesRateLow
                Unsigned32,
            hwXQoSHardPipeAccessStatisticsExtPassBytesRateHigh
                Unsigned32,
            hwXQoSHardPipeAccessStatisticsExtDiscardPacketsRateLow
                Unsigned32,
            hwXQoSHardPipeAccessStatisticsExtDiscardPacketsRateHigh
                Unsigned32,
            hwXQoSHardPipeAccessStatisticsExtDiscardBytesRateLow
                Unsigned32,
            hwXQoSHardPipeAccessStatisticsExtDiscardBytesRateHigh
                Unsigned32
            }

    hwXQoSHardPipeAccessStatisticsExtInterfaceIndex  OBJECT-TYPE
        SYNTAX   InterfaceIndex
        MAX-ACCESS read-only
        STATUS current
        DESCRIPTION
            " This object indicates the access interface index. "
        ::= { hwXQoSHardPipeAccessStatisticsExtEntry 1 }

    hwXQoSHardPipeAccessStatisticsExtDirection  OBJECT-TYPE
        SYNTAX INTEGER
            {
                inbound(1),
                outbound(2)
            }
        MAX-ACCESS read-only
        STATUS current
        DESCRIPTION
            " This object indicates the direction where access hard pipe statistics are queried.
              The value can be:
              1: inbound
              2: outbound  "
        ::= { hwXQoSHardPipeAccessStatisticsExtEntry 2 }

      hwXQoSHardPipeAccessStatisticsExtReset  OBJECT-TYPE
            SYNTAX INTEGER
            {
                reset(1)
            }
            MAX-ACCESS read-write
            STATUS current
            DESCRIPTION
                " This object indicates the statistics are reset.  "
            ::= { hwXQoSHardPipeAccessStatisticsExtEntry 3 }

      hwXQoSHardPipeAccessStatisticsExtPassPacketsLow OBJECT-TYPE
            SYNTAX  Unsigned32
            MAX-ACCESS read-only
            STATUS current
            DESCRIPTION
                " This object indicates the number of passed packets. "
            ::= { hwXQoSHardPipeAccessStatisticsExtEntry 4 }

      hwXQoSHardPipeAccessStatisticsExtPassPacketsHigh OBJECT-TYPE
            SYNTAX  Unsigned32
            MAX-ACCESS read-only
            STATUS current
            DESCRIPTION
                " This object indicates the number of passed packets. "
            ::= { hwXQoSHardPipeAccessStatisticsExtEntry 5 }

      hwXQoSHardPipeAccessStatisticsExtPassBytesLow OBJECT-TYPE
            SYNTAX  Unsigned32
            MAX-ACCESS read-only
            STATUS current
            DESCRIPTION
                " This object indicates the number of  passed bytes. "
            ::= { hwXQoSHardPipeAccessStatisticsExtEntry 6 }

      hwXQoSHardPipeAccessStatisticsExtPassBytesHigh OBJECT-TYPE
            SYNTAX  Unsigned32
            MAX-ACCESS read-only
            STATUS current
            DESCRIPTION
                " This object indicates the number of  passed bytes. "
            ::= { hwXQoSHardPipeAccessStatisticsExtEntry 7 }

      hwXQoSHardPipeAccessStatisticsExtDiscardPacketsLow OBJECT-TYPE
            SYNTAX  Unsigned32
            MAX-ACCESS read-only
            STATUS current
            DESCRIPTION
                " This object indicates the number of discarded packets."
            ::= { hwXQoSHardPipeAccessStatisticsExtEntry 8 }

      hwXQoSHardPipeAccessStatisticsExtDiscardPacketsHigh OBJECT-TYPE
            SYNTAX  Unsigned32
            MAX-ACCESS read-only
            STATUS current
            DESCRIPTION
                " This object indicates the number of discarded packets."
            ::= { hwXQoSHardPipeAccessStatisticsExtEntry 9 }

      hwXQoSHardPipeAccessStatisticsExtDiscardBytesLow OBJECT-TYPE
            SYNTAX  Unsigned32
            MAX-ACCESS read-only
            STATUS current
            DESCRIPTION
                " This object indicates the number of discarded bytes. "
            ::= { hwXQoSHardPipeAccessStatisticsExtEntry 10 }

      hwXQoSHardPipeAccessStatisticsExtDiscardBytesHigh OBJECT-TYPE
            SYNTAX  Unsigned32
            MAX-ACCESS read-only
            STATUS current
            DESCRIPTION
                " This object indicates the number of discarded bytes. "
            ::= { hwXQoSHardPipeAccessStatisticsExtEntry 11 }

      hwXQoSHardPipeAccessStatisticsExtPassPacketsRateLow OBJECT-TYPE
            SYNTAX  Unsigned32
            MAX-ACCESS read-only
            STATUS current
            DESCRIPTION
                " The value of this object identifies the rate of pass packets."
            ::= { hwXQoSHardPipeAccessStatisticsExtEntry 12 }

      hwXQoSHardPipeAccessStatisticsExtPassPacketsRateHigh OBJECT-TYPE
            SYNTAX  Unsigned32
            MAX-ACCESS read-only
            STATUS current
            DESCRIPTION
                " The value of this object identifies the rate of pass packets."
            ::= { hwXQoSHardPipeAccessStatisticsExtEntry 13 }

      hwXQoSHardPipeAccessStatisticsExtPassBytesRateLow OBJECT-TYPE
            SYNTAX  Unsigned32
            MAX-ACCESS read-only
            STATUS current
            DESCRIPTION
                " The value of this object identifies the rate of pass bytes. "
            ::= { hwXQoSHardPipeAccessStatisticsExtEntry 14 }

      hwXQoSHardPipeAccessStatisticsExtPassBytesRateHigh OBJECT-TYPE
            SYNTAX  Unsigned32
            MAX-ACCESS read-only
            STATUS current
            DESCRIPTION
                " The value of this object identifies the rate of pass bytes. "
            ::= { hwXQoSHardPipeAccessStatisticsExtEntry 15 }

      hwXQoSHardPipeAccessStatisticsExtDiscardPacketsRateLow OBJECT-TYPE
            SYNTAX  Unsigned32
            MAX-ACCESS read-only
            STATUS current
            DESCRIPTION
                " The value of this object identifies the rate of discarded packets."
            ::= { hwXQoSHardPipeAccessStatisticsExtEntry 16 }

      hwXQoSHardPipeAccessStatisticsExtDiscardPacketsRateHigh OBJECT-TYPE
            SYNTAX  Unsigned32
            MAX-ACCESS read-only
            STATUS current
            DESCRIPTION
                " The value of this object identifies the rate of discarded packets."
            ::= { hwXQoSHardPipeAccessStatisticsExtEntry 17 }

      hwXQoSHardPipeAccessStatisticsExtDiscardBytesRateLow OBJECT-TYPE
            SYNTAX  Unsigned32
            MAX-ACCESS read-only
            STATUS current
            DESCRIPTION
                " The value of this object identifies the rate of discarded bytes."
            ::= { hwXQoSHardPipeAccessStatisticsExtEntry 18 }

      hwXQoSHardPipeAccessStatisticsExtDiscardBytesRateHigh OBJECT-TYPE
            SYNTAX  Unsigned32
            MAX-ACCESS read-only
            STATUS current
            DESCRIPTION
                " The value of this object identifies the rate of discarded bytes."
            ::= { hwXQoSHardPipeAccessStatisticsExtEntry 19 }

    hwXQoSCompliances  OBJECT IDENTIFIER ::=   { hwXQoSConformance 1 }
    hwXQoSGroups       OBJECT IDENTIFIER ::=   { hwXQoSConformance 2 }

    -- compliance statements

    hwXQoSCompliance MODULE-COMPLIANCE
        STATUS      current
        DESCRIPTION
            "The compliance statement for entities that implement
        extend QoS on a router."

        MODULE -- this module
        MANDATORY-GROUPS {
            hwXQoSIfQueueGroup,
            hwXQoSIfCarStatisticsGroup,
            hwXQoSCpDefendStatisticsGroup,
            hwNotificationExtGroup,
            hwXQosAtmTrafficQueueGroup,
            hwXQosAtmPvcServiceTypeGroup,
            hwXQosIfOutboundQueueStatisticGroup,
            hwXQoSBaGroup,
            hwXQoSBa8021pPhbGroup,
            hwXQoSBa8021pMapGroup,
            hwXQoSBaDscpPhbGroup,
            hwXQoSBaDscpMapGroup,
            hwXQoSBaExpPhbGroup,
            hwXQoSBaExpMapGroup,
            hwXQoSIfDiffDomainGroup,
            hwXQoSIfTrust8021pGroup,
            hwXQoSCommonInboundGroup,
            hwXQoSPppInboundGroup,
            hwXQoSServiceclassGroup,
            hwXQoSPhbGroup,
            hwXQoSFieldDeiGroup,
            hwXQoSPicForwardingGroup,
            hwXQoSCarTableGroup,
            hwXQoSPortShapingGroup,
            hwXQoSQueueGroup,
            hwXQoSCarStatisticsGroup,
            hwXQoSCpRateLimitGroup}
        ::= { hwXQoSCompliances 1 }

    -- units of conformance

    hwXQoSIfQueueGroup OBJECT-GROUP
        OBJECTS {
            hwXQoSIfQueueIfIndex,
            hwXQoSIfQueueVlanID,
            hwXQoSIfQueueCosType,
            hwXQoSIfQueuePassedPackets,
            hwXQoSIfQueuePassededBytes,
            hwXQoSIfQueueTotalPackets,
            hwXQoSIfQueueTotalBytes,
            hwXQoSIfQueueDiscardedPackets,
            hwXQoSIfQueueDiscardedBytes,
            hwXQoSIfQueuePassedPacketRate,
            hwXQoSIfQueuePassedByteRate,
            hwXQoSIfQueueDiscardedPacketRate,
            hwXQoSIfQueueDiscardedByteRate,
            hwXQoSIfQueueResetFlag,
            hwXQoSIfQueueUsagePercentage,
            hwXQoSIfQueueDropTailDiscardedPackets,
            hwXQoSIfQueueDropTailDiscardedBytes,
            hwXQoSIfQueueWredDiscardedPackets,
            hwXQoSIfQueueWredDiscardedBytes,
            hwXQoSIfQueueDropTailDiscardedPacketRate,
            hwXQoSIfQueueDropTailDiscardedByteRate,
            hwXQoSIfQueueWredDiscardedPacketRate,
            hwXQoSIfQueueWredDiscardedByteRate,
            hwXQoSIfQueueStatisticsTrafficTowardThisPort,
            hwXQoSIfQueueStatisticsPhysicalBandwidthOfPortQoS
        }
        STATUS      current
        DESCRIPTION
            "This is a optional group of information."
        ::= { hwXQoSGroups 1 }

    hwXQoSIfCarStatisticsGroup OBJECT-GROUP
        OBJECTS {
            hwXQoSIfCarConformedPackets,
            hwXQoSIfCarConformedBytes,
            hwXQoSIfCarConformedPacketRate,
            hwXQoSIfCarConformedByteRate,
            hwXQoSIfCarExceededPackets,
            hwXQoSIfCarExceededBytes,
            hwXQoSIfCarExceededPacketRate,
            hwXQoSIfCarExceededByteRate,
            hwXQoSIfCarOverflowPackets,
            hwXQoSIfCarOverflowBytes,
            hwXQoSIfCarOverflowPacketRate,
            hwXQoSIfCarOverflowByteRate,
            hwXQoSIfCarPassedPackets,
            hwXQoSIfCarPassedBytes,
            hwXQoSIfCarDiscardedPackets,
            hwXQoSIfCarDiscardedBytes
        }
        STATUS      current
        DESCRIPTION
            "This is a optional group of information."
        ::= { hwXQoSGroups 2 }

    hwXQoSCpDefendStatisticsGroup OBJECT-GROUP
        OBJECTS {
            hwXQoSCpDefendSlotId,
            hwXQoSCpDefendObjectIndex,
            hwXQoSCpDefendPassedPackets,
            hwXQoSCpDefendPassedBytes,
            hwXQoSCpDefendPassedPacketRate,
            hwXQoSCpDefendPassedByteRate,
            hwXQoSCpDefendDiscardedPackets,
            hwXQoSCpDefendDiscardedBytes,
            hwXQoSCpDefendDiscardedPacketRate,
            hwXQoSCpDefendDiscardedByteRate,
            hwXQoSCpDefendDiscardedThreshold,
            hwXQoSCpDefendChassisID,
            hwXQoSCpDefendProtocolDescirption,
            hwXQoSCpDefendIntfPassedNum
        }
        STATUS current
        DESCRIPTION
            "This is a optional group of information."
        ::= { hwXQoSGroups 3 }

    hwNotificationExtGroup NOTIFICATION-GROUP
        NOTIFICATIONS {
            hwXQoSCpDefendDiscardedRateAlarm,
            hwXQoSCpDefendDiscardedPacketAlarm,
            hwXQoSQueueDiscardThresholdTrap,
            hwXQoSStormControlTrap,
            hwXQoSCprlDiscardedPacketAlarm,
            hwXQoSCprlDiscardedPacketAlarmClear,
            hwXQoSRedirectNextHopChangedAlarm,
            hwXQoSSecurityStormControlInterfaceTrap,
            hwXQoSIrsmDelayAlarm,
            hwXQoSIrsmSynFrameDropAlarm,
            hwXQoSStatResouceNotEnoughAlarm,
            hwXQoSIrsmDropPacketAlarm,
            hwXQoSRuleFailAlarm,
            hwXQoSCpDefendDiscardedPacketAlarmClear,
            hwXQoSCARResouceNotEnoughAlarm,
            hwXQoSPortQueueAlarmClear,
            hwXQoSProfileUsedAlarm,
            hwXQoSPortQueueAlarm,
            hwXQoSHardPipeAlarm,
            hwXQoSHardPipeAlarmClear,
            hwXQoSSoftPipeAlarm,
            hwXQoSSoftPipeAlarmClear,
            hwXQoSHardPipeBwAlarm,
            hwXQoSHardPipeBwAlarmClear,
            hwXQOSQueueBufferOverrunAlarm,
            hwXQOSQueueBufferOverrunResume,
            hwXQoSIfLrDiscardAlarm,
            hwXQoSIfLrDiscardAlarmResume,
            hwXQoSFCoEPriorityAlarm,
            hwXQoSFCoEPriorityAlarmClear,
            hwXQoSVpnAclConflictAlarm, --add by wangjing
            hwXQoSVpnAclConflictAlarmClear,   --add by wangjing
            hwXQoSDefendPortCarPassedPacketAlarm,
            hwXQoSDefendPortCarPassedPacketAlarmClear,
            hwXQoSMulticastPktsDiscardAlarm,  --add by pengsheng
            hwXQoSMulticastPktsDiscardAlarmResume,  --add by pengsheng
            hwXQoSMulticastPktsDiscardInterfaceAlarm,  --add by pengsheng
            hwXQoSMulticastPktsDiscardInterfaceAlarmResume,  --add by pengsheng
            hwXQoSUnicastPktsCongestionInterfaceAlarm,  --add by zhouzaihua
            hwXQoSUnicastPktsCongestionInterfaceAlarmResume,  --add by zhouzaihua
            hwXQoSPacketsDropInterfaceAlarm,  --add by zhouzaihua
            hwXQoSPacketsDropInterfaceAlarmResume,  --add by zhouzaihua
            hwXQoSRcyPortPktsDropAlarm,  --add by zhouzaihua
            hwXQoSRcyPortPktsDropAlarmResume,  --add by zhouzaihua
            hwXQoSUnicastPktsDiscardAlarm,  --add by zhouzaihua
            hwXQoSUnicastPktsDiscardAlarmResume,  --add by zhouzaihua
            hwXQoSIfCarDiscardAlarm,  --add by zhouzaihua
            hwXQoSIfCarDiscardAlarmResume,  --add by zhouzaihua
            hwXQoSStormSuppressAlarm,        --add by sunqirui
            hwXQoSStormSuppressAlarmResume,  --add by sunqirui
            hwXQoSStormSuppressSlotAlarm,        --add by chensenfa
            hwXQoSStormSuppressSlotAlarmResume,   --add by chensenfa
            hwXQoSIngressPktsDiscardAlarm,  --add by zhouzaihua
            hwXQoSIngressPktsDiscardAlarmResume,  --add by zhouzaihua
            hwXQoSIngressAgingDiscardAlarm,  --add by zhouzaihua
            hwXQoSIngressAgingDiscardAlarmResume, --add by zhouzaihua
            hwXQosQueueExcepAlarm,         --add by hehaiyan
            hwXQosQueueExcepAlarmResume,  --add by hehaiyan
            hwXQoSPfcTurnOffAlarm,         --add by hehaiyan
            hwXQoSPfcTurnOffResume,  --add by hehaiyan
            hwXQoSPfcDeadLockAlarm,         --add by hehaiyan
            hwXQoSPfcDeadLockResume,  --add by hehaiyan
            hwXACLFEIMemoryFullAlarm,   --add by wangyan
            hwXACLFEIMemoryFullAlarmResume, --add by wangyan
            hwXQoSInterfaceIngressDropAlarm,  --add by zhouzaihua
            hwXQoSInterfaceIngressDropAlarmResume,  --add by zhouzaihua
            hwXQoSTMPerformanceAlarm,  --add by gaolikun
            hwXQoSTMPerformanceAlarmClear,  --add by gaolikun
            hwXACLEPGCreateGroupAlarm,  --add by zhaoqingqing
            hwXACLEPGCreateGroupResume, --add by zhaoqingqing
            hwXACLEPGGroupMemberAlarm,  --add by zhaoqingqing
            hwXACLEPGGroupMemberResume, --add by zhaoqingqing
            hwXACLEPGPolicyAlarm,      --add by zhaoqingqing
            hwXACLEPGPolicyResume,       --add by zhaoqingqing
            hwXQoSPfcApplyFailAlarm,         --add by pengsheng
            hwXQoSPfcApplyFailAlarmResume,   --add by pengsheng
            hwXACLEPGEnableAlarm,    --add by zhaoqingqing
            hwXACLEPGEnableResume,    --add by zhaoqingqing
            hwXQOSFlowControlAlarm,     --add by shenjiulong
            hwXQOSFlowControlAlarmResume,    --add by shenjiulong
            hwXACLResourceAlarm,      --add by xuehui
            hwXACLResourceAlarmResume,      --add by xuehui
            hwEnpPerformanceAlarm,      --add by shenlin
            hwEnpPerformanceAlarmResume,     --add by shenlin
            hwXACLEPGGroupMemberV6Alarm,  --add by dingsong
            hwXACLEPGGroupMemberV6Resume, --add by dingsong
            hwXQoSModeChannelOverPortShapAlarm, --add by guohongbo
            hwXQoSModeChannelOverPortShapAlarmClear, --add by guohongbo
            hwXQoSPfcInnerDeadLockAlarm,   --add by maoyingxia
            hwXQoSPfcInnerDeadLockResume,  --add by maoyingxia
            hwXQoSVlanStormSuppressAlarm,   --add by dujianghai
            hwXQoSVlanStormSuppressAlarmResume,  --add by dujianghai
            hwXQoSBDStormSuppressAlarm,   --add by dujianghai
            hwXQoSBDStormSuppressAlarmResume,  --add by dujianghai
            hwXQoSInterfaceDownRedirectNextHopInvalidAlarm,  --add by qixin
            hwXQoSInterfaceDownRedirectNextHopInvalidAlarmClear,  --add by qixin
            hwXQoSRedirectNextHopEventLog,  --add by qixin
            hwXQoSBgpFlowspecDestinationOriginAsOverAlarm,  --add by qixin
            hwXQoSBgpFlowspecDestinationOriginAsOverAlarmClear,  --add by qixin
            hwXQoSOutPfcTurnOffAlarm,         --add by wangjian
            hwXQoSOutPfcTurnOffResume,  --add by wangjian
            hwXQoSUserQueueApplyPirExhaustionAlarm,  --add by qixin
            hwXQoSUserQueueApplyPirExhaustionResume,  --add by qixin
            hwXQoSUserQueueApplyPirPreAlarm,  --add by qixin
            hwXQoSUserQueueApplyPirPreResume,  --add by qixin
            hwXQoSUserQueuePirAdjustAlarm,  --add by qixin
            hwXQoSUserQueuePirAdjustResume,  --add by qixin
            hwXQoSModuleAlarmPatchStub,          --add by qiaojuyang
            hwXQoSModuleAlarmPatchStubResume,     --add by qiaojuyang
            hwXQoSSlotAlarmPatchStub,            --add by qiaojuyang
            hwXQoSSlotAlarmPatchStubResume,       --add by qiaojuyang
            hwXQoSDevAlarmPatchStub,             --add by qiaojuyang
            hwXQoSDevAlarmPatchStubResume,        --add by qiaojuyang
            hwXQoSUnsupportedActionAlarm,  --add by qixin
            hwXQoSUnsupportedActionResume,  --add by qixin
            hwXQoSModeFlexeOverPortShapAlarm, --add by tanyashi
            hwXQoSModeFlexeOverPortShapAlarmClear, --add by tanyashi
            hwXQoSCarBindwidthExceedChipLimitAlarm,
            hwXQoSCarBindwidthExceedChipLimitResume,
            hwXQoSModeChannelOverEthBnBwdAlarm,
            hwXQoSModeChannelOverEthBnBwdResume,
            hwXACLEPGRuleAlarm,       --add by yanghao
            hwXACLEPGRuleResume, --add by yanghao
            hwXQoSBoardHQoSFailAlarm,
            hwXQoSBoardHQoSFailResume,
            hwXQoSInterfaceHQoSFailAlarm,
            hwXQoSInterfaceHQoSFailResume,
            hwXQoSReceivedMultiPauseFrameInterfaceDownAlarm,
            hwXQoSReceivedMultiPauseFrameInterfaceDownResume,
            hwXQoSTrunkTrafficCongestionAlarm,
            hwXQoSTrunkTrafficCongestionResume,
            hwXQoSFwdResourceOverload,
            hwXQoSFwdResourceOverloadResume,
            hwXQoSBoardServiceMismatchEvent,
            hwXQoSSlotTrafficCongestionAlarm,
            hwXQoSSlotTrafficCongestionResume,
		    hwXQoSChipBufferOverrunAlarm,
		    hwXQoSChipBufferOverrunResume,
            hwXQoSPfcRxRateAlarm,
            hwXQoSPfcRxRateResume,
            hwXQoSPfcTxRateAlarm,
            hwXQoSPfcTxRateResume,
            hwXQosHeadRoomPoolApplyFailAlarm,
            hwXQosHeadRoomPoolApplyFailAlarmResume,
            hwXQosPfcBufferApplyFailAlarm,
            hwXQosPfcBufferApplyFailAlarmResume,
            hwXQoSFlowspecNotSupportBoardEvent,
            hwXQoSBgpFlowspecDestinationOriginAsOverIPv6Alarm,
            hwXQoSBgpFlowspecDestinationOriginAsOverIPv6AlarmClear,
            hwXQoSBgpFlowspecDestinationCommunityOverAlarm,
            hwXQoSBgpFlowspecDestinationCommunityOverAlarmClear,
            hwXQoSTrafficPolicyRuleResoucePreAlarm,
            hwXQoSTrafficPolicyRuleResoucePreAlarmResume,
            hwXQoSFLowMatrixRailInvalidAlarm,
            hwXQoSFLowMatrixRailInvalidAlarmResume,
            hwXQoSBgpFlowspecDDoSLowPriorityAlarm,
            hwXQoSBgpFlowspecDDoSLowPriorityAlarmClear
        }
        STATUS  current
        DESCRIPTION
            "The HUAWEI defend trap info."
        ::= { hwXQoSGroups 4 }

    hwXQoSGeneralGroup OBJECT-GROUP
        OBJECTS {
        hwXQoSFrameId,
        hwXQoSSlotId,
        hwXQoSPortId,
        hwXQoSTrapIfName,
        hwXQoSTrapQueueId,
        hwXQoSTrapDiscardPackets
        }
        STATUS  current
        DESCRIPTION
            "This is a optional group of information."
        ::= { hwXQoSGroups 5 }

    hwXQoSSredGroup OBJECT-GROUP
        OBJECTS {
            hwXQoSIfSredRedStartDiscardPoint,
            hwXQoSIfSredRedDiscardProbability,
            hwXQoSIfSredYellowStartDiscardPoint,
            hwXQoSIfSredYellowDiscardProbability,
            hwXQoSIfSredRowStatus
        }
        STATUS  current
        DESCRIPTION
            "This is Sred group of information."
        ::= { hwXQoSGroups 6 }

    hwXQosAtmTrafficQueueGroup OBJECT-GROUP
        OBJECTS {
            hwXQoSAtmTrafficQueueServiceClass,
            hwXQoSAtmTrafficQueueRowStatus
        }
        STATUS current
        DESCRIPTION
            "This is a optional group of information."
        ::= { hwXQoSGroups 7 }
    hwXQosAtmPvcServiceTypeGroup OBJECT-GROUP
        OBJECTS {
            hwXQoSAtmPvcNameServiceTypeIndex,
            hwXQoSAtmPvcServiceType,
            hwXQoSAtmPvcPcr,
            hwXQoSAtmPvcCdvt,
            hwXQoSAtmPvcVbrScr,
            hwXQoSAtmPvcVbrMbs,
            hwXQoSAtmPvcRowStatus
        }
        STATUS current
        DESCRIPTION
            "This is a optional group of information."
        ::= { hwXQoSGroups 8 }

    hwXQosIfOutboundQueueStatisticGroup OBJECT-GROUP
    OBJECTS {
        hwXQoSIfQueDiscardPackets
    }
    STATUS current
    DESCRIPTION
         "This is a optional group of information."
     ::= { hwXQoSGroups 9 }

    hwXQoSShapingGroup OBJECT-GROUP
        OBJECTS {
            hwXQoSIfShapingQueueCir,
            hwXQoSIfShapingQueuePir,
            hwXQoSIfShapingRowStatus
        }
        STATUS  current
        DESCRIPTION
        "This is Shaping group of information."
        ::= { hwXQoSGroups 10 }

    hwXQoSUrpfDiscardStatisticsGroup OBJECT-GROUP
        OBJECTS {
            hwXQoSUrpfDiscardedPackets
        }
        STATUS  current
        DESCRIPTION
            "This is a optional group of information."
        ::= { hwXQoSGroups 11 }

    hwXQoSBaGroup OBJECT-GROUP
        OBJECTS { hwXQoSBaIndex, hwXQoSBaName, hwXQoSBaRowStatus }
        STATUS current
        DESCRIPTION
            "This is different server domain  group of information."
        ::= { hwXQoSGroups 12 }

    hwXQoSBa8021pPhbGroup OBJECT-GROUP
        OBJECTS { hwXQoSBa8021pPhbIndex, hwXQoSBa8021pPhbPri, hwXQoSBa8021pPhbCos, hwXQoSBa8021pPhbColour, hwXQoSBa8021pPhbRowStatus
             }
        STATUS current
        DESCRIPTION
            "This is different server domain  group of information."
        ::= { hwXQoSGroups 13 }

    hwXQoSBa8021pMapGroup OBJECT-GROUP
        OBJECTS { hwXQoSBa8021pMapIndex, hwXQoSBa8021pMapCos, hwXQoSBa8021pMapColour, hwXQoSBa8021pMapPri, hwXQoSBa8021pMapRowStatus
             }
        STATUS current
        DESCRIPTION
            "This is different server domain  group of information."
        ::= { hwXQoSGroups 14 }

    hwXQoSBaDscpPhbGroup OBJECT-GROUP
        OBJECTS { hwXQoSBaDscpPhbIndex, hwXQoSBaDscpPhbPri, hwXQoSBaDscpPhbCos, hwXQoSBaDscpPhbColour, hwXQoSBaDscpPhbRowStatus
             }
        STATUS current
        DESCRIPTION
            "This is different server domain  group of information."
        ::= { hwXQoSGroups 15 }

    hwXQoSBaDscpMapGroup OBJECT-GROUP
        OBJECTS { hwXQoSBaDscpMapIndex, hwXQoSBaDscpMapCos, hwXQoSBaDscpMapColour, hwXQoSBaDscpMapPri, hwXQoSBaDscpMapRowStatus
             }
        STATUS current
        DESCRIPTION
            "This is different server domain  group of information."
        ::= { hwXQoSGroups 16 }

    hwXQoSBaExpPhbGroup OBJECT-GROUP
        OBJECTS { hwXQoSBaExpPhbIndex, hwXQoSBaExpPhbPri, hwXQoSBaExpPhbCos, hwXQoSBaExpPhbColour, hwXQoSBaExpPhbRowStatus
             }
        STATUS current
        DESCRIPTION
            "This is different server domain  group of information."
        ::= { hwXQoSGroups 17 }

    hwXQoSBaExpMapGroup OBJECT-GROUP
        OBJECTS { hwXQoSBaExpMapIndex, hwXQoSBaExpMapCos, hwXQoSBaExpMapColour, hwXQoSBaExpMapPri, hwXQoSBaExpMapRowStatus
             }
        STATUS current
        DESCRIPTION
            "This is different server domain  group of information."
        ::= { hwXQoSGroups 18 }

    hwXQoSIfDiffDomainGroup OBJECT-GROUP
        OBJECTS { hwXQoSIfDiffDomainIfIndex, hwXQoSIfDiffDomainVlanId, hwXQoSIfDiffDomainName, hwXQoSIfDiffDomainRowStatus, hwXQoSIfDiffDomainVlanId2
             }
        STATUS current
        DESCRIPTION
            "This is different server domain  group of information."
        ::= { hwXQoSGroups 19 }

    hwXQoSBaPhbGroup OBJECT-GROUP
        OBJECTS { hwXQoSBaPhbCos, hwXQoSBaPhbColour, hwXQoSBaPhbRowStatus
             }
        STATUS current
        DESCRIPTION
            "This is different server domain  group of information."
        ::= { hwXQoSGroups 20 }

    hwXQoSBaMapGroup OBJECT-GROUP
        OBJECTS { hwXQoSBaMapPri, hwXQoSBaMapRowStatus
             }
        STATUS current
        DESCRIPTION
            "This is different server domain  group of information."
        ::= { hwXQoSGroups 21 }

    hwXQoSIfTrustGroup OBJECT-GROUP
        OBJECTS { hwXQoSIfTrustAction,
            hwXQoSIfTrustRowStatus}
        STATUS current
        DESCRIPTION
            "This is different server domain  group of information."
        ::= { hwXQoSGroups 22 }

        hwXQosVlanStatGroup OBJECT-GROUP
            OBJECTS {hwXQosVlanStatInTotalPkts, hwXQosVlanStatInTotalBytes, hwXQosVlanStatOutTotalPkts, hwXQosVlanStatOutTotalBytes,
                hwXQosVlanStatInUcastPkts, hwXQosVlanStatInUcastBytes, hwXQosVlanStatOutUcastPkts, hwXQosVlanStatOutUcastBytes, hwXQosVlanStatInMcastPkts,
                hwXQosVlanStatInMcastBytes, hwXQosVlanStatOutMcastPkts, hwXQosVlanStatOutMcastBytes, hwXQosVlanStatInBcastPkts, hwXQosVlanStatInBcastBytes,
                hwXQosVlanStatOutBcastPkts, hwXQosVlanStatOutBcastBytes, hwXQosVlanStatInUnknownUcastPkts, hwXQosVlanStatInUnknownUcastBytes, hwXQosVlanStatResetFlag
                }
            STATUS current
            DESCRIPTION
                "This is statistic group of information."
            ::= { hwXQoSGroups 23 }

        hwXQoSVlanCfgGroup OBJECT-GROUP
            OBJECTS { hwXQoSVlanStatEnable }
            STATUS current
            DESCRIPTION
                "This is statistic group of information."
            ::= { hwXQoSGroups 24 }

     hwXQoSStormControlGroup OBJECT-GROUP
         OBJECTS {
            hwXQoSStormControlBroadcastMinRate,
            hwXQoSStormControlBroadcastMaxRate,
            hwXQoSStormControlMulticastMinRate,
            hwXQoSStormControlMulticastMaxRate,
            hwXQoSStormControlAction,
            hwXQoSStormControlInterval,
            hwXQoSStormControlTrapEnable,
            hwXQoSStormControlLogEnable,
            hwXQoSStormControlStatus,
            hwXQoSStormControlUnicastMinRate,
            hwXQoSStormControlUnicastMaxRate,
            hwXQoSStormControlBcMode,
            hwXQoSStormControlMcMode,
            hwXQoSStormControlUcMode
        }
    STATUS current
    DESCRIPTION
    "This is shaping group of information."
    ::= { hwXQoSGroups 25 }
    hwXQoSQueueStatisticsGroup OBJECT-GROUP
        OBJECTS {
            hwXQoSQueueStatisticsPassedPacketsCount,
            hwXQosQueueStatisticsReset,
            hwXQoSQueueStatisticsRowStatus
        }
        STATUS current
        DESCRIPTION
            "This is shaping group of information."
        ::= { hwXQoSGroups 26}

    hwXQoSIfPppoeGroup OBJECT-GROUP
        OBJECTS {
            hwXQoSIfPppoeRowStatus
        }
        STATUS current
        DESCRIPTION
            "This is PPPoE group of information."
        ::= { hwXQoSGroups 27 }

    hwXQoSVlanBcastSuppressGroup OBJECT-GROUP
        OBJECTS {
            hwXQoSVlanBcastSuppressValue,
            hwXQoSVlanBcastSuppressRowStatus
        }
        STATUS current
        DESCRIPTION
            "This is VLAN broadcast suppression group of information."
        ::= { hwXQoSGroups 28 }

    hwXQoSRedirectNextHopGroup OBJECT-GROUP
        OBJECTS {
            hwXQoSRedirectNextHopBehaviorName,
            hwXQoSRedirectNextHopOldIp,
            hwXQoSRedirectNextHopNewIp
                }
        STATUS  current
        DESCRIPTION
            "This is the redirect next hop group of information."
        ::= { hwXQoSGroups 29 }


    hwXQoSIfTrust8021pGroup OBJECT-GROUP
        OBJECTS {
            hwXQoSIfTrust8021pIfIndex,
            hwXQoSIfTrust8021pVlanID,
            hwXQoSIfTrust8021pAction,
            hwXQoSIfTrust8021pRowStatus
            }
        STATUS current
        DESCRIPTION
            "Description."
        ::= { hwXQoSGroups 30}

    hwXQoSCommonInboundGroup OBJECT-GROUP
        OBJECTS{
            hwXQoSCommonInboundPhbIndex,
            hwXQoSCommonInboundPhbCos,
            hwXQoSCommonInboundPhbColor,
            hwXQoSCommonInboundPhbPri,
            hwXQoSCommonInboundRowStatus
            }
        STATUS current
        DESCRIPTION
            " hwXQoSCommonInboundGroup "
        ::= { hwXQoSGroups 31 }



    hwXQoSPppInboundGroup OBJECT-GROUP
        OBJECTS{
            hwXQoSPppInboundCos,
            hwXQoSPppInboundColor,
            hwXQoSPppInboundRowStatus
             }
        STATUS current
        DESCRIPTION
            " hwXQoSPppInboundGroup "
        ::= { hwXQoSGroups 32 }



    hwXQoSServiceclassGroup OBJECT-GROUP
        OBJECTS{
            hwXQoSServiceclassPort,
            hwXQoSServiceclass,
            hwXQoSServiceclassRowStatus
            }
        STATUS current
        DESCRIPTION
            " hwXQoSServiceclassGroup "
        ::= { hwXQoSGroups 33 }



    hwXQoSPhbGroup OBJECT-GROUP
        OBJECTS{
            hwXQoSPhbPort,
            hwXQoSPhbEnable,
            hwXQoSPhbRowStatus
            }
        STATUS current
        DESCRIPTION
            " hwXQoSPhbGroup "
        ::= { hwXQoSGroups 34 }

    hwXQoSFieldDeiGroup OBJECT-GROUP
        OBJECTS{
            hwXQoSFieldDeiInterface,
            hwXQoSFieldDeiVlanId,
            hwXQoSFieldDeiEnabled,
            hwXQoSFieldDeiRowStatus
            }
        STATUS current
        DESCRIPTION
            " hwXQoSFieldDeiGroup "
        ::= { hwXQoSGroups 35 }

    hwXQoSPicForwardingGroup OBJECT-GROUP
        OBJECTS{
            hwXQoSPicForwardingInterface,
            hwXQoSPicForwarding8021pValue,
            hwXQoSPicForwardingPriority,
            hwXQoSPicForwardingRowStatus
            }
        STATUS current
        DESCRIPTION
            " hwXQoSPicForwardingGroup "
        ::= { hwXQoSGroups 36 }

    hwXQoSCarTableGroup OBJECT-GROUP
        OBJECTS{
            hwXQoSCarInterfaceIndex,
            hwXQoSCarDirection,
            hwXQoSCarVlanID,
            hwXQoSCarCirValue,
            hwXQoSCarPirValue,
            hwXQoSCarCbsValue,
            hwXQoSCarPbsValue,
            hwXQoSCarGreenAction,
            hwXQoSCarGreenServiceClass,
            hwXQoSCarGreenColor,
            hwXQoSCarYellowAction,
            hwXQoSCarYellowServiceClass,
            hwXQoSCarYellowColor,
            hwXQoSCarRedAction,
            hwXQoSCarRedServiceClass,
            hwXQoSCarRedColor,
            hwXQoSCarRowStatus
             }
        STATUS current
        DESCRIPTION
            " hwXQoSCarTableGroup "
        ::= { hwXQoSGroups 37 }

    hwXQoSPortShapingGroup OBJECT-GROUP
        OBJECTS{
            hwXQoSPortShapingInterface,
            hwXQoSPortShapingValue,
            hwXQoSPortShapingPbsValue,
            hwXQoSPortShapPercent,
            hwXQoSPortShapingRowStatus
            }
        STATUS current
        DESCRIPTION
            " hwXQoSPortShapingGroup "
        ::= { hwXQoSGroups 38 }

    hwXQoSQueueGroup OBJECT-GROUP
        OBJECTS{
            hwXQoSQueueInterfaceIndex,
            hwXQoSQueueServiceClass,
            hwXQoSQueueCirValue,
            hwXQoSQueueCirPercentage,
            hwXQoSQueueDirection,
            hwXQoSQueueRowStatus
            }
        STATUS current
        DESCRIPTION
            " hwXQoSQueueGroup "
        ::= { hwXQoSGroups 39 }

    hwXQoSCarStatisticsGroup OBJECT-GROUP
        OBJECTS{
            hwXQoSCarStatisticsInterfaceIndex,
            hwXQoSCarStatisticsDirection,
            hwXQoSCarStatisticsVlanid,
            hwXQoSCarStatisticsSlotNumber,
            hwXQoSCarStatisticsReset,
            hwXQoSCarStatisticsPassPackets,
            hwXQoSCarStatisticsPassBytes,
            hwXQoSCarStatisticsDropPackets,
            hwXQoSCarStatisticsDropBytes,
            hwXQoSCarStatisticsPassPacketsRate,
            hwXQoSCarStatisticsPassBytesRate,
            hwXQoSCarStatisticsDropPacketsRate,
            hwXQoSCarStatisticsDropBytesRate
            }
        STATUS current
        DESCRIPTION
            " hwXQoSCarStatisticsGroup "
        ::= { hwXQoSGroups 40 }

    hwXQoSCpRateLimitGroup OBJECT-GROUP
        OBJECTS{
            hwXQoSCpRateLimitIfIndex,
            hwXQoSCpRateLimitPeVidValue,
            hwXQoSCpRateLimitCeVidBegin,
            hwXQoSCpRateLimitCeVidEnd,
            hwXQoSCpRateLimitType,
            hwXQoSCpRateLimitIgmpCir,
            hwXQoSCpRateLimitIgmpCbs,
            hwXQoSCpRateLimitRowStatus
                }
        STATUS current
        DESCRIPTION
            " hwXQoSCpRateLimitGroup "
        ::= { hwXQoSGroups 41 }

    hwXQoSPortQueueStatisticsGroup OBJECT-GROUP
        OBJECTS {
            hwXQoSPortQueueStatisticsInterfaceIndex,
            hwXQoSPortQueueStatisticsDirection,
            hwXQoSPortQueueStatisticsQueueIndex,
            hwXQoSPortQueueStatisticsReset,
            hwXQoSPortQueueStatisticsTotalPassPackets,
            hwXQoSPortQueueStatisticsTotalPassBytes,
            hwXQoSPortQueueStatisticsTotalDiscardPackets,
            hwXQoSPortQueueStatisticsTotalDiscardBytes,
            hwXQoSPortQueueStatisticsDropTailDiscardPackets,
            hwXQoSPortQueueStatisticsDropTailDiscardBytes,
            hwXQoSPortQueueStatisticsWredDiscardPackets,
            hwXQoSPortQueueStatisticsWredDiscardBytes,
            hwXQoSPortQueueStatisticsPassPacketsRate,
            hwXQoSPortQueueStatisticsPassBytesRate,
            hwXQoSPortQueueStatisticsDiscardPacketsRate,
            hwXQoSPortQueueStatisticsDiscardBytesRate,
            hwXQoSPortQueueStatisticsDropTailDiscardPacketsRate,
            hwXQoSPortQueueStatisticsDropTailDiscardBytesRate,
            hwXQoSPortQueueStatisticsWredDiscardPacketsRate,
            hwXQoSPortQueueStatisticsWredDiscardBytesRate,
            hwXQoSPortQueueStatisticsTrafficTowardThisPort,
            hwXQoSPortQueueStatisticsPhysicalBandwidthOfPortQoS,
            hwXQoSPortQueueStatisticsQueuePercentage,
            hwXQoSPortQueueStatisticsTotalPackets,
            hwXQoSPortQueueStatisticsTotalBytes
        }
        STATUS current
        DESCRIPTION
            "Description."
        ::= { hwXQoSGroups 42 }

    hwXQoSPortStatisticsDropGroup OBJECT-GROUP
        OBJECTS {
            hwXQoSPortStatisticsDropPacketsCount,
            hwXQosPortStatisticsDropReset,
            hwXQosPortStatisticsDropResetTime
        }
        STATUS current
        DESCRIPTION
                "This is the drop packets statistics of port group of information."
        ::= { hwXQoSGroups 43}

    hwXQoSQueueStatisticsDropGroup OBJECT-GROUP
        OBJECTS {
            hwXQoSQueueStatisticsDropPacketsCount,
            hwXQosQueueStatisticsDropReset,
            hwXQosQueueStatisticsDropResetTime
        }
        STATUS current
        DESCRIPTION
            "This is the drop packets statistics of queue group of information."
        ::= { hwXQoSGroups 44}

    hwXQoSIfScheduleGroup OBJECT-GROUP
        OBJECTS {
            hwXQoSIfScheduleProfile,
            hwXQoSIfScheduleRowStatus
        }
        STATUS current
        DESCRIPTION
            "This is Interface schedule group of information."
        ::= { hwXQoSGroups 45 }

    hwXQoSScheduleProfileGroup OBJECT-GROUP
        OBJECTS {
            hwXQoSScheduleQueueMode,
            hwXQoSScheduleQueueBeWeight,
            hwXQoSScheduleQueueAf1Weight,
            hwXQoSScheduleQueueAf2Weight,
            hwXQoSScheduleQueueAf3Weight,
            hwXQoSScheduleQueueAf4Weight,
            hwXQoSScheduleQueueCs6Weight,
            hwXQoSScheduleQueueCs7Weight,
            hwXQoSScheduleQueueEfWeight,
            hwXQoSScheduleProfileRowStatus
        }
        STATUS current
        DESCRIPTION
            "This is schedule profile group of information."
        ::= { hwXQoSGroups 46 }

    hwXQoSQppbPolicyGroup OBJECT-GROUP
        OBJECTS {
            hwXQoSQppbPolicyStatisticsInterfaceIndex,
            hwXQoSQppbPolicyDirection,
            hwXQoSQppbPolicyLocalID,
            hwXQoSQppbPolicyStatisticsReset,
            hwXQoSQppbPolicyMatchedPackets,
            hwXQoSQppbPolicyMatchedBytes,
            hwXQoSQppbPolicyPassedPackets,
            hwXQoSQppbPolicyPassedBytes,
            hwXQoSQppbPolicyDropedPackets,
            hwXQoSQppbPolicyDropedBytes
        }
        STATUS current
        DESCRIPTION
            "Description."
        ::= { hwXQoSGroups 47 }

        hwXQoSStatResouceNotEnoughAlarmGroup OBJECT-GROUP
            OBJECTS { hwXQoSStatResouceNotEnoughSlotId, hwXQoSStatResouceNotEnoughStatType }
            STATUS current
            DESCRIPTION
                "Description."
            ::= { hwXQoSGroups 48 }

        hwXQoSCARResouceNotEnoughAlarmGroup OBJECT-GROUP
            OBJECTS { hwXQoSCARResouceNotEnoughSlotId, hwXQoSCARResouceNotEnoughCARType }
            STATUS current
            DESCRIPTION
                "Description."
            ::= { hwXQoSGroups 49 }

    hwXQoSHardPipeAccessStatisticsGroup OBJECT-GROUP
        OBJECTS {
            hwXQoSHardPipeAccessStatisticsInterfaceIndex,
            hwXQoSHardPipeAccessStatisticsReset,
            hwXQoSHardPipeAccessStatisticsPassPackets,
            hwXQoSHardPipeAccessStatisticsPassBytes,
            hwXQoSHardPipeAccessStatisticsDiscardPackets,
            hwXQoSHardPipeAccessStatisticsDiscardBytes,
            hwXQoSHardPipeAccessStatisticsPassPacketsRate,
            hwXQoSHardPipeAccessStatisticsPassBytesRate,
            hwXQoSHardPipeAccessStatisticsDiscardPacketsRate,
            hwXQoSHardPipeAccessStatisticsDiscardBytesRate
        }
        STATUS      current
        DESCRIPTION
            "This is a group of HardPipe stastitics for access interfaces."
        ::= { hwXQoSGroups 51 }

    hwXQoSSecurityStormControlInterfaceObjects OBJECT IDENTIFIER ::= { hwXQoSObjects 21 }

    hwXQoSSecurityStormControlInterfaceTable OBJECT-TYPE
        SYNTAX SEQUENCE OF HwXQoSSecurityStormControlInterfaceEntry
        MAX-ACCESS not-accessible
        STATUS current
        DESCRIPTION
            "A Table about storm-control interface information."
        ::= { hwXQoSSecurityStormControlInterfaceObjects 1 }

    hwXQoSSecurityStormControlInterfaceEntry OBJECT-TYPE
        SYNTAX HwXQoSSecurityStormControlInterfaceEntry
        MAX-ACCESS not-accessible
        STATUS current
        DESCRIPTION
            "Description."
        INDEX { hwXQoSSecurityStormControlInterfaceChassisId,
                hwXQoSSecurityStormControlInterfaceSlotId
              }
        ::= { hwXQoSSecurityStormControlInterfaceTable 1 }

    HwXQoSSecurityStormControlInterfaceEntry ::=
        SEQUENCE {
            hwXQoSSecurityStormControlInterfaceChassisId
                Integer32,
            hwXQoSSecurityStormControlInterfaceSlotId
                Integer32,
            hwXQoSSecurityStormControlInterfaceName
                OCTET STRING,
            hwXQoSSecurityStormControlInterfaceVlan
                Integer32
            }

    hwXQoSSecurityStormControlInterfaceChassisId OBJECT-TYPE
        SYNTAX Integer32 (1..128)
        MAX-ACCESS read-only
        STATUS current
        DESCRIPTION
            "The chassis ID indicates the slot on which chassis is configured with storm control."
        ::= { hwXQoSSecurityStormControlInterfaceEntry 1 }

    hwXQoSSecurityStormControlInterfaceSlotId OBJECT-TYPE
        SYNTAX Integer32 (1..128)
        MAX-ACCESS read-only
        STATUS current
        DESCRIPTION
            "The slot configured with storm control."
        ::= { hwXQoSSecurityStormControlInterfaceEntry 2 }

    hwXQoSSecurityStormControlInterfaceName OBJECT-TYPE
        SYNTAX OCTET STRING (SIZE (0..63))
        MAX-ACCESS read-only
        STATUS current
        DESCRIPTION
            "The interface name."
        ::= { hwXQoSSecurityStormControlInterfaceEntry 3 }

    hwXQoSSecurityStormControlInterfaceVlan OBJECT-TYPE
        SYNTAX Integer32 (0..4095)
        MAX-ACCESS read-only
        STATUS current
        DESCRIPTION
            "The value of this object identifies the VLAN ID of the interface."
        ::= { hwXQoSSecurityStormControlInterfaceEntry 4 }

    hwXQoSQppbPolicyApplyFailAlarmObjects OBJECT IDENTIFIER ::= { hwXQoSObjects 26 }

    hwXQoSQppbPolicyApplyFailAlarmTable OBJECT-TYPE
        SYNTAX SEQUENCE OF HwXQoSQppbPolicyApplyFailAlarmEntry
        MAX-ACCESS not-accessible
        STATUS current
        DESCRIPTION
            "It will alarm when the qos-local-id has exceed the upper-limit."
        ::= { hwXQoSQppbPolicyApplyFailAlarmObjects 1 }

    hwXQoSQppbPolicyApplyFailAlarmEntry OBJECT-TYPE
        SYNTAX HwXQoSQppbPolicyApplyFailAlarmEntry
        MAX-ACCESS not-accessible
        STATUS current
        DESCRIPTION
            "It will alarm when the qos-local-id has exceed the upper-limit."
        INDEX { hwXQoSQppbPolicyApplyFailChassisID, hwXQoSQppbPolicyApplyFailSlotId, hwXQoSQppbPolicyApplyFailInterfaceName, hwXQoSQppbPolicyApplyFailDirection, hwXQoSQppbPolicyApplyFailLocalID }
        ::= { hwXQoSQppbPolicyApplyFailAlarmTable 1 }

    HwXQoSQppbPolicyApplyFailAlarmEntry ::=
        SEQUENCE {
            hwXQoSQppbPolicyApplyFailChassisID
                Integer32,
            hwXQoSQppbPolicyApplyFailSlotId
                Integer32,
            hwXQoSQppbPolicyApplyFailInterfaceName
                OCTET STRING,
            hwXQoSQppbPolicyApplyFailDirection
                INTEGER,
            hwXQoSQppbPolicyApplyFailLocalID
                Integer32
            }

    hwXQoSQppbPolicyApplyFailChassisID OBJECT-TYPE
        SYNTAX Integer32 (1..128)
        MAX-ACCESS read-only
        STATUS current
        DESCRIPTION
            "Chassis ID of the LPU where the qppb policy been applied failed."
        ::= { hwXQoSQppbPolicyApplyFailAlarmEntry 1 }

    hwXQoSQppbPolicyApplyFailSlotId OBJECT-TYPE
        SYNTAX Integer32 (1..128)
        MAX-ACCESS read-only
        STATUS current
        DESCRIPTION
            "Slot ID of the LPU where the qppb policy been applied failed."
        ::= { hwXQoSQppbPolicyApplyFailAlarmEntry 2 }

    hwXQoSQppbPolicyApplyFailInterfaceName OBJECT-TYPE
        SYNTAX OCTET STRING
        MAX-ACCESS read-only
        STATUS current
        DESCRIPTION
            "Name of the interface where the qppb policy been applied failed."
        ::= { hwXQoSQppbPolicyApplyFailAlarmEntry 3 }

    hwXQoSQppbPolicyApplyFailDirection OBJECT-TYPE
        SYNTAX INTEGER
            {
                inbound(1),
                outbound(2)
            }
        MAX-ACCESS read-only
        STATUS current
        DESCRIPTION
            "Direction of the qppb policy."
        ::= { hwXQoSQppbPolicyApplyFailAlarmEntry 4 }

    hwXQoSQppbPolicyApplyFailLocalID OBJECT-TYPE
        SYNTAX Integer32 (1..128)
        MAX-ACCESS read-only
        STATUS current
        DESCRIPTION
            "LocalID of the qppb policy."
        ::= { hwXQoSQppbPolicyApplyFailAlarmEntry 5 }

    hwXQoSIfQPPBDelAlarmObjects OBJECT IDENTIFIER ::= { hwXQoSObjects 27 }

    hwXQoSIfQPPBDelAlarmTable OBJECT-TYPE
        SYNTAX SEQUENCE OF HwXQoSIfQPPBDelAlarmEntry
        MAX-ACCESS not-accessible
        STATUS current
        DESCRIPTION
            "It will alarm when the interface qppb policy deleted because of conflict."
        ::= { hwXQoSIfQPPBDelAlarmObjects 1 }

    hwXQoSIfQPPBDelAlarmEntry OBJECT-TYPE
        SYNTAX HwXQoSIfQPPBDelAlarmEntry
        MAX-ACCESS not-accessible
        STATUS current
        DESCRIPTION
            "It will alarm when the interface qppb policy deleted because of conflict."
        INDEX { hwXQoSIfQPPBDelInterfaceName, hwXQoSIfQPPBDelPolicyName, hwXQoSIfQPPBDelDirection, hwXQoSIfQPPBDelDiscrip }
        ::= { hwXQoSIfQPPBDelAlarmTable 1 }

    HwXQoSIfQPPBDelAlarmEntry ::=
        SEQUENCE {
            hwXQoSIfQPPBDelInterfaceName
                OCTET STRING,
            hwXQoSIfQPPBDelPolicyName
                OCTET STRING,
            hwXQoSIfQPPBDelDirection
                INTEGER,
            hwXQoSIfQPPBDelDiscrip
                OCTET STRING
        }

    hwXQoSIfQPPBDelInterfaceName OBJECT-TYPE
        SYNTAX OCTET STRING
        MAX-ACCESS read-only
        STATUS current
        DESCRIPTION
            "Name of the interface when the interface qppb policy deleted because of conflict."
        ::= { hwXQoSIfQPPBDelAlarmEntry 1 }

    hwXQoSIfQPPBDelPolicyName OBJECT-TYPE
        SYNTAX OCTET STRING
        MAX-ACCESS read-only
        STATUS current
        DESCRIPTION
            "Name of the QPPB Policy when the interface qppb policy deleted because of conflict."
        ::= { hwXQoSIfQPPBDelAlarmEntry 2 }

    hwXQoSIfQPPBDelDirection OBJECT-TYPE
        SYNTAX INTEGER
        {
            inbound(1),
            outbound(2)
        }
        MAX-ACCESS read-only
        STATUS current
        DESCRIPTION
            "Direction of the qppb policy."
        ::= { hwXQoSIfQPPBDelAlarmEntry 3 }

    hwXQoSIfQPPBDelDiscrip OBJECT-TYPE
        SYNTAX OCTET STRING
        MAX-ACCESS read-only
        STATUS current
        DESCRIPTION
            "precautions descirption."
        ::= { hwXQoSIfQPPBDelAlarmEntry 4 }

 -- 1.3.6.1.4.1.2011.5.25.32.4.2.2.50
    hwXQosCarResourceGroup OBJECT-GROUP
        OBJECTS { hwXQosCarResourceDirection, hwXQosCarResourceSlotNumber, hwXQosCarResourceServiceType, hwXQosCarResourceTotalValue, hwXQosCarResourceAllocatedValue, hwXQosCarResourceFreeValue }
        STATUS current
        DESCRIPTION
            "This is CAR Resource group of information."
        ::= { hwXQoSGroups 50 }

 -- QoS Buffer Statistic
    hwXQoSBufferStatisticObjects OBJECT IDENTIFIER ::= { hwXQoSObjects 28 }

 -- Buffer overrun
    hwXQoSBufferThresholdTable OBJECT-TYPE
        SYNTAX SEQUENCE OF HwXQoSBufferThresholdEntry
        MAX-ACCESS not-accessible
        STATUS current
        DESCRIPTION
            "A table of QoS buffer overrun threshold configuration information."
        ::= { hwXQoSBufferStatisticObjects 1 }

    hwXQoSBufferThresholdEntry OBJECT-TYPE
        SYNTAX HwXQoSBufferThresholdEntry
        MAX-ACCESS not-accessible
        STATUS current
        DESCRIPTION
            "QoS buffer overrun threshold configuration Entry."
        INDEX { hwXQoSBufferThresholdVrId }
        ::= { hwXQoSBufferThresholdTable 1 }

    HwXQoSBufferThresholdEntry ::=
        SEQUENCE {
            hwXQoSBufferThresholdVrId
                Integer32,
            hwXQoSBufferThreshold
                Integer32,
            hwXQoSBufferThresholdStatus
                RowStatus
         }

    hwXQoSBufferThresholdVrId OBJECT-TYPE
        SYNTAX Integer32
        MAX-ACCESS read-only
        STATUS current
        DESCRIPTION
            "VS index."
        ::= { hwXQoSBufferThresholdEntry 1 }

    hwXQoSBufferThreshold OBJECT-TYPE
        SYNTAX Integer32
        MAX-ACCESS read-create
        STATUS current
        DESCRIPTION
            "QoS buffer overrun threshold value."
        ::= { hwXQoSBufferThresholdEntry 2 }

    hwXQoSBufferThresholdStatus OBJECT-TYPE
        SYNTAX RowStatus
        MAX-ACCESS read-create
        STATUS current
        DESCRIPTION
            "RowStatus. Three actions are used: active,
            createAndGo, destroy"
        ::= { hwXQoSBufferThresholdEntry 3 }

--  Buffer alarm
    EnableFlagType ::= TEXTUAL-CONVENTION
    STATUS current
    DESCRIPTION
        "The enable flag."
    SYNTAX INTEGER
        {
            enable(1),
            disable(2)
        }

    hwXQoSBufferAlarmTable OBJECT-TYPE
        SYNTAX SEQUENCE OF HwXQoSBufferAlarmEntry
        MAX-ACCESS not-accessible
        STATUS current
        DESCRIPTION
            "A table of QoS buffer overrun Alarm configuration information."
        ::= { hwXQoSBufferStatisticObjects 2 }


    hwXQoSBufferAlarmEntry OBJECT-TYPE
        SYNTAX HwXQoSBufferAlarmEntry
        MAX-ACCESS not-accessible
        STATUS current
        DESCRIPTION
            "QoS buffer overrun Alarm configuration Entry."
        INDEX { hwXQoSBufferAlarmVrId }
        ::= { hwXQoSBufferAlarmTable 1 }

    HwXQoSBufferAlarmEntry ::=
        SEQUENCE {
            hwXQoSBufferAlarmVrId
                Integer32,
            hwXQoSBufferAlarmEnable
                EnableFlagType
        }

    hwXQoSBufferAlarmVrId OBJECT-TYPE
        SYNTAX Integer32
        MAX-ACCESS read-only
        STATUS current
        DESCRIPTION
            "VS index."
        ::= { hwXQoSBufferAlarmEntry 1 }

    hwXQoSBufferAlarmEnable OBJECT-TYPE
        SYNTAX EnableFlagType
        MAX-ACCESS read-write
        STATUS current
        DESCRIPTION
            "QoS buffer overrun alarm enable flag: enable(1), disable(2)."
        ::= { hwXQoSBufferAlarmEntry 2 }

 -- buffer overrun history
    hwXQoSBufferOverrunHistoryTable OBJECT-TYPE
        SYNTAX SEQUENCE OF HwXQoSBufferOverrunHistoryEntry
        MAX-ACCESS not-accessible
        STATUS current
        DESCRIPTION
            "A table of QoS buffer overrun history information."
        ::= { hwXQoSBufferStatisticObjects 3 }


    hwXQoSBufferOverrunHistoryEntry OBJECT-TYPE
        SYNTAX HwXQoSBufferOverrunHistoryEntry
        MAX-ACCESS not-accessible
        STATUS current
        DESCRIPTION
            "QoS buffer overrun history Entry."
        INDEX { hwXQosBufferOverrunHistoryIfindex, hwXQosBufferOverrunHistoryQueueId, hwXQoSBufferOverrunHistoryChasisId, hwXQoSBufferOverrunHistorySlotId, hwXQoSBufferOverrunHistoryNumberId }
        ::= { hwXQoSBufferOverrunHistoryTable 1 }


    HwXQoSBufferOverrunHistoryEntry ::=
        SEQUENCE {
            hwXQosBufferOverrunHistoryIfindex
                Integer32,
            hwXQosBufferOverrunHistoryQueueId
                Integer32,
            hwXQoSBufferOverrunHistoryChasisId
                Integer32,
            hwXQoSBufferOverrunHistorySlotId
                Integer32,
            hwXQoSBufferOverrunHistoryNumberId
                Integer32,
            hwXQoSBufferOverrunHistoryReset
                INTEGER,
            hwXQosBufferOverrunHistoryUsedLength
                Counter64,
            hwXQoSBufferOverrunHistoryTime
                OCTET STRING
        }

    hwXQosBufferOverrunHistoryIfindex OBJECT-TYPE
        SYNTAX Integer32
        MAX-ACCESS read-only
        STATUS current
        DESCRIPTION
            "The interface index."
        ::= { hwXQoSBufferOverrunHistoryEntry 1 }

    hwXQosBufferOverrunHistoryQueueId OBJECT-TYPE
        SYNTAX Integer32 (0..7)
        MAX-ACCESS read-only
        STATUS current
        DESCRIPTION
            "The interface queue index. The value ranges from 0 to 7."
        ::= { hwXQoSBufferOverrunHistoryEntry 2 }

    hwXQoSBufferOverrunHistoryChasisId OBJECT-TYPE
        SYNTAX Integer32 (0..255)
        MAX-ACCESS read-only
        STATUS current
        DESCRIPTION
            "Chasis index."
        ::= { hwXQoSBufferOverrunHistoryEntry 3 }

    hwXQoSBufferOverrunHistorySlotId OBJECT-TYPE
        SYNTAX Integer32 (0..255)
        MAX-ACCESS read-only
        STATUS current
        DESCRIPTION
            "Slot index."
        ::= { hwXQoSBufferOverrunHistoryEntry 4 }

    hwXQoSBufferOverrunHistoryNumberId OBJECT-TYPE
        SYNTAX Integer32 (1..5)
        MAX-ACCESS read-only
        STATUS current
        DESCRIPTION
            "Number index. The value ranges from 1 to 5."
        ::= { hwXQoSBufferOverrunHistoryEntry 5 }

    hwXQoSBufferOverrunHistoryReset OBJECT-TYPE
        SYNTAX INTEGER
        {
            reset(1),
            none(2)
        }
        MAX-ACCESS read-create
        STATUS current
        DESCRIPTION
            " This object indicates the resetting of statistics. "
        ::= { hwXQoSBufferOverrunHistoryEntry 6 }

    hwXQosBufferOverrunHistoryUsedLength OBJECT-TYPE
        SYNTAX Counter64
        MAX-ACCESS read-only
        STATUS current
        DESCRIPTION
            "The used kbyte number of interface buffer."
        ::= { hwXQoSBufferOverrunHistoryEntry 7 }

    hwXQoSBufferOverrunHistoryTime OBJECT-TYPE
        SYNTAX OCTET STRING (SIZE (1..20))
        MAX-ACCESS read-only
        STATUS current
        DESCRIPTION
            "Buffer overrun system time."
        ::= { hwXQoSBufferOverrunHistoryEntry 8 }

    hwRemoteMirrRecoverFailNotify NOTIFICATION-TYPE
        STATUS current
        DESCRIPTION
            "Remote mirror recover fail notify"
        ::= { hwXQoSObjects 29 }


    hwXQoSGlbQPPBEventLogObjects OBJECT IDENTIFIER ::= { hwXQoSObjects 30 }

    hwXQoSGlbQPPBEventTable OBJECT-TYPE
        SYNTAX SEQUENCE OF HwXQoSGlbQPPBEventEntry
        MAX-ACCESS not-accessible
        STATUS current
        DESCRIPTION
            "The event occurs when The global QPPB will not be effective."
        ::= { hwXQoSGlbQPPBEventLogObjects 1 }

    hwXQoSGlbQPPBEventEntry OBJECT-TYPE
        SYNTAX HwXQoSGlbQPPBEventEntry
        MAX-ACCESS not-accessible
        STATUS current
        DESCRIPTION
            "The event occurs when The global QPPB will not be effective."
        INDEX { hwXQoSGlbQPPBEventSlotId, hwXQoSGlbQPPBEventFunction, hwXQoSGlbQPPBEventDiscrip }
        ::= { hwXQoSGlbQPPBEventTable 1 }

    HwXQoSGlbQPPBEventEntry ::=
        SEQUENCE {
            hwXQoSGlbQPPBEventSlotId
                OCTET STRING,
            hwXQoSGlbQPPBEventFunction
                OCTET STRING,
            hwXQoSGlbQPPBEventDiscrip
                OCTET STRING
        }
    hwXQoSGlbQPPBEventSlotId OBJECT-TYPE
        SYNTAX OCTET STRING
        MAX-ACCESS read-only
        STATUS current
        DESCRIPTION
            "Slot ID of the LPU when The global QPPB will not be effective."
        ::= { hwXQoSGlbQPPBEventEntry 1 }

    hwXQoSGlbQPPBEventFunction OBJECT-TYPE
        SYNTAX OCTET STRING
        MAX-ACCESS read-only
        STATUS current
        DESCRIPTION
            "function of qppb when The global QPPB will not be effective."
        ::= { hwXQoSGlbQPPBEventEntry 2 }

    hwXQoSGlbQPPBEventDiscrip OBJECT-TYPE
        SYNTAX OCTET STRING
        MAX-ACCESS read-only
        STATUS current
        DESCRIPTION
            "precautions descirption."
        ::= { hwXQoSGlbQPPBEventEntry 3 }


    hwXQoSQppbPolicyEventLogObjects OBJECT IDENTIFIER ::= { hwXQoSObjects 31 }

    hwXQoSQppbPolicyEventTable OBJECT-TYPE
        SYNTAX SEQUENCE OF HwXQoSQppbPolicyEventEntry
        MAX-ACCESS not-accessible
        STATUS current
        DESCRIPTION
            "The event occurs when the QPPB policy will not be effective."
        ::= { hwXQoSQppbPolicyEventLogObjects 1 }

    hwXQoSQppbPolicyEventEntry OBJECT-TYPE
        SYNTAX HwXQoSQppbPolicyEventEntry
        MAX-ACCESS not-accessible
        STATUS current
        DESCRIPTION
            "The event occurs when the QPPB policy will not be effective."
        INDEX { hwXQoSQppbPolicyChassisID, hwXQoSQppbPolicySlotId }
        ::= { hwXQoSQppbPolicyEventTable 1 }

    HwXQoSQppbPolicyEventEntry ::=
        SEQUENCE {
            hwXQoSQppbPolicyChassisID
                Integer32,
            hwXQoSQppbPolicySlotId
                Integer32 }

    hwXQoSQppbPolicyChassisID OBJECT-TYPE
        SYNTAX Integer32 (1..128)
        MAX-ACCESS read-only
        STATUS current
        DESCRIPTION
            "Chassis ID of the LPU where the QPPB policy will not be effective."
        ::= { hwXQoSQppbPolicyEventEntry 1 }

    hwXQoSQppbPolicySlotId OBJECT-TYPE
        SYNTAX Integer32 (1..128)
        MAX-ACCESS read-only
        STATUS current
        DESCRIPTION
            "Slot ID of the LPU where the QPPB policy will not be effective."
        ::= { hwXQoSQppbPolicyEventEntry 2 }


    hwXQoSMulticastPktsDiscardAlarmObjects OBJECT IDENTIFIER ::= { hwXQoSObjects 32 }

    hwXQoSMulticastPktsDiscardAlarmTable OBJECT-TYPE
        SYNTAX SEQUENCE OF HwXQoSMulticastPktsDiscardAlarmEntry
        MAX-ACCESS not-accessible
        STATUS current
        DESCRIPTION
            "hwXQoSMulticastPktsDiscardAlarmTable"
        ::= { hwXQoSMulticastPktsDiscardAlarmObjects 1 }

    hwXQoSMulticastPktsDiscardAlarmEntry OBJECT-TYPE
        SYNTAX HwXQoSMulticastPktsDiscardAlarmEntry
        MAX-ACCESS not-accessible
        STATUS current
        DESCRIPTION
            "hwXQoSMulticastPktsDiscardAlarmEntry"
        INDEX { hwXQoSMulticastPktsDiscardAlarmSlotid }
        ::= { hwXQoSMulticastPktsDiscardAlarmTable 1 }

    HwXQoSMulticastPktsDiscardAlarmEntry ::=
        SEQUENCE {
            hwXQoSMulticastPktsDiscardAlarmSlotid
                OCTET STRING
                }

    hwXQoSMulticastPktsDiscardAlarmSlotid OBJECT-TYPE
        SYNTAX OCTET STRING
        MAX-ACCESS read-only
        STATUS current
        DESCRIPTION
            "slot id."
        ::= { hwXQoSMulticastPktsDiscardAlarmEntry 1 }

    hwXQoSMulticastPktsDiscardInterfaceAlarmTable OBJECT-TYPE
        SYNTAX SEQUENCE OF HwXQoSMulticastPktsDiscardInterfaceAlarmEntry
        MAX-ACCESS not-accessible
        STATUS current
        DESCRIPTION
            "hwXQoSMulticastPktsDiscardInterfaceAlarmTable"
        ::= { hwXQoSMulticastPktsDiscardAlarmObjects 2 }

    hwXQoSMulticastPktsDiscardInterfaceAlarmEntry OBJECT-TYPE
        SYNTAX HwXQoSMulticastPktsDiscardInterfaceAlarmEntry
        MAX-ACCESS not-accessible
        STATUS current
        DESCRIPTION
            "hwXQoSMulticastPktsDiscardInterfaceAlarmEntry"
        INDEX { hwXQoSMulticastPktsDiscardInterfaceAlarmIfIndex }
        ::= { hwXQoSMulticastPktsDiscardInterfaceAlarmTable 1 }

    HwXQoSMulticastPktsDiscardInterfaceAlarmEntry ::=
        SEQUENCE {
            hwXQoSMulticastPktsDiscardInterfaceAlarmIfIndex
                InterfaceIndex,
            hwXQoSMulticastPktsDiscardInterfaceAlarmIfName
                OCTET STRING
                }

    hwXQoSMulticastPktsDiscardInterfaceAlarmIfIndex OBJECT-TYPE
        SYNTAX InterfaceIndex
        MAX-ACCESS read-only
        STATUS current
        DESCRIPTION
            "The index of physical interface."
        ::= { hwXQoSMulticastPktsDiscardInterfaceAlarmEntry 1 }

    hwXQoSMulticastPktsDiscardInterfaceAlarmIfName OBJECT-TYPE
        SYNTAX OCTET STRING
        MAX-ACCESS read-only
        STATUS current
        DESCRIPTION
            "The name of physical interface."
        ::= { hwXQoSMulticastPktsDiscardInterfaceAlarmEntry 2 }


    hwXQoSCarObjects OBJECT IDENTIFIER ::= { hwXQoSObjects 33 }

    hwXQoSCarCfgInfoTable OBJECT-TYPE
        SYNTAX SEQUENCE OF HwXQoSCarCfgInfoEntry
        MAX-ACCESS not-accessible
        STATUS current
        DESCRIPTION
            "A table of QoS CAR configuration information."
        ::= { hwXQoSCarObjects 1 }

    hwXQoSCarCfgInfoEntry OBJECT-TYPE
        SYNTAX HwXQoSCarCfgInfoEntry
        MAX-ACCESS not-accessible
        STATUS current
        DESCRIPTION
            "QoS CAR configuration information Entry."
        INDEX { hwXQoSCarIndex }
        ::= { hwXQoSCarCfgInfoTable 1 }

    HwXQoSCarCfgInfoEntry ::=
        SEQUENCE {
            hwXQoSCarIndex
                Unsigned32,
            hwXQoSCarName
                OCTET STRING,
            hwXQoSCarCir
                Unsigned32,
            hwXQoSCarPir
                Unsigned32,
            hwXQoSCarCbs
                Unsigned32,
            hwXQoSCarPbs
                Unsigned32,
            hwXQoSCarCfgRowStatus
                RowStatus,
            hwXQoSCarPercent
                Unsigned32
                }

    hwXQoSCarIndex OBJECT-TYPE
        SYNTAX Unsigned32
        MAX-ACCESS read-create
        STATUS current
        DESCRIPTION
            "This object indicates the index of the QoS CAR template."
        ::= { hwXQoSCarCfgInfoEntry 1 }

    hwXQoSCarName OBJECT-TYPE
        SYNTAX OCTET STRING (SIZE (1..31))
        MAX-ACCESS read-create
        STATUS current
        DESCRIPTION
            "This object indicates the name of the QoS CAR template."
        ::= { hwXQoSCarCfgInfoEntry 2 }

    hwXQoSCarCir OBJECT-TYPE
        SYNTAX Unsigned32
        MAX-ACCESS read-create
        STATUS current
        DESCRIPTION
            "The value of this object identifies the Committed Information Rate (unit: kbps)."
        ::= { hwXQoSCarCfgInfoEntry 3 }

    hwXQoSCarPir OBJECT-TYPE
        SYNTAX Unsigned32
        MAX-ACCESS read-create
        STATUS current
        DESCRIPTION
            "The value of this object identifies the Peak Information Rate (unit: kbps)."
        ::= { hwXQoSCarCfgInfoEntry 4 }

    hwXQoSCarCbs OBJECT-TYPE
        SYNTAX Unsigned32
        MAX-ACCESS read-create
        STATUS current
        DESCRIPTION
            "The value of this object identifies the Committed Burst Size (unit: bytes)."
        ::= { hwXQoSCarCfgInfoEntry 5 }

    hwXQoSCarPbs OBJECT-TYPE
        SYNTAX Unsigned32
        MAX-ACCESS read-create
        STATUS current
        DESCRIPTION
            "The value of this object identifies the Peak Burst Size (unit: bytes)."
        ::= { hwXQoSCarCfgInfoEntry 6 }

    hwXQoSCarCfgRowStatus OBJECT-TYPE
        SYNTAX RowStatus
        MAX-ACCESS read-create
        STATUS current
        DESCRIPTION
            "RowStatus. Three actions are used: active, createAndGo, destroy."
        ::= { hwXQoSCarCfgInfoEntry 7 }

    hwXQoSCarPercent OBJECT-TYPE
        SYNTAX Unsigned32
        MAX-ACCESS read-only
        STATUS current
        DESCRIPTION
            "The value of this object identifies the Percentage of the Bandwidth Rate as the CIR(unit: percent)."
        ::= { hwXQoSCarCfgInfoEntry 8 }

    hwXQoSCarIfApplyTable OBJECT-TYPE
        SYNTAX SEQUENCE OF HwXQoSCarIfApplyEntry
        MAX-ACCESS not-accessible
        STATUS current
        DESCRIPTION
            "A table of QoS CAR applied on interface."
        ::= { hwXQoSCarObjects 2 }

    hwXQoSCarIfApplyEntry OBJECT-TYPE
        SYNTAX HwXQoSCarIfApplyEntry
        MAX-ACCESS not-accessible
        STATUS current
        DESCRIPTION
            "QoS CAR application information on interface."
        INDEX { hwXQoSCarIfApplyIfIndex }
        ::= { hwXQoSCarIfApplyTable 1 }

    HwXQoSCarIfApplyEntry ::=
        SEQUENCE {
            hwXQoSCarIfApplyIfIndex
                Unsigned32,
            hwXQoSCarIfApplyDirection
                INTEGER,
            hwXQoSCarIfApplyQosCarName
                OCTET STRING,
            hwXQoSCarIfApplyRowStatus
                RowStatus
                }

    hwXQoSCarIfApplyIfIndex OBJECT-TYPE
        SYNTAX Unsigned32
        MAX-ACCESS read-create
        STATUS current
        DESCRIPTION
            "The index of physical interface."
        ::= { hwXQoSCarIfApplyEntry 1 }

    hwXQoSCarIfApplyDirection OBJECT-TYPE
        SYNTAX INTEGER
        {
            inbound(0),
            outbound(1)
        }
        MAX-ACCESS read-create
        STATUS current
        DESCRIPTION
            "The direction of QoS CAR application."
        ::= { hwXQoSCarIfApplyEntry 2 }

    hwXQoSCarIfApplyQosCarName OBJECT-TYPE
        SYNTAX OCTET STRING (SIZE (1..31))
        MAX-ACCESS read-create
        STATUS current
        DESCRIPTION
            "The name of QoS CAR."
        ::= { hwXQoSCarIfApplyEntry 3 }

    hwXQoSCarIfApplyRowStatus OBJECT-TYPE
        SYNTAX RowStatus
        MAX-ACCESS read-create
        STATUS current
        DESCRIPTION
            "RowStatus. Three actions are used: active, createAndGo, destroy."
        ::= { hwXQoSCarIfApplyEntry 4 }

    hwXQoSCarIfApplyStatisticsTable OBJECT-TYPE
        SYNTAX SEQUENCE OF HwXQoSCarIfApplyStatisticsEntry
        MAX-ACCESS not-accessible
        STATUS current
        DESCRIPTION
            "A table of QoS CAR statistics information."
        ::= { hwXQoSCarObjects 3 }

    hwXQoSCarIfApplyStatisticsEntry OBJECT-TYPE
        SYNTAX HwXQoSCarIfApplyStatisticsEntry
        MAX-ACCESS not-accessible
        STATUS current
        DESCRIPTION
            "Statistics information of QoS CAR."
        INDEX { hwXQoSCarIfApplyStatIfIndex }
        ::= { hwXQoSCarIfApplyStatisticsTable 1 }

    HwXQoSCarIfApplyStatisticsEntry ::=
        SEQUENCE {
            hwXQoSCarIfApplyStatIfIndex
                Unsigned32,
            hwXQoSCarIfApplyStatQosCarName
                OCTET STRING,
            hwXQoSCarIfApplyStatPassPackets
                Counter64,
            hwXQoSCarIfApplyStatPassBytes
                Counter64,
            hwXQoSCarIfApplyStatDiscardPackets
                Counter64,
            hwXQoSCarIfApplyStatDiscardBytes
                Counter64,
            hwXQoSCarIfApplyStatResetFlag
                EnabledStatus
                }

    hwXQoSCarIfApplyStatIfIndex OBJECT-TYPE
        SYNTAX Unsigned32
        MAX-ACCESS read-only
        STATUS current
        DESCRIPTION
            "The index of physical interface."
        ::= { hwXQoSCarIfApplyStatisticsEntry 1 }

    hwXQoSCarIfApplyStatQosCarName OBJECT-TYPE
        SYNTAX OCTET STRING (SIZE (1..31))
        MAX-ACCESS read-only
        STATUS current
        DESCRIPTION
            "The name of QoS CAR."
        ::= { hwXQoSCarIfApplyStatisticsEntry 2 }

    hwXQoSCarIfApplyStatPassPackets OBJECT-TYPE
        SYNTAX Counter64
        MAX-ACCESS read-only
        STATUS current
        DESCRIPTION
            "Passed packets."
        ::= { hwXQoSCarIfApplyStatisticsEntry 3 }

    hwXQoSCarIfApplyStatPassBytes OBJECT-TYPE
        SYNTAX Counter64
        MAX-ACCESS read-only
        STATUS current
        DESCRIPTION
            "Passed bytes."
        ::= { hwXQoSCarIfApplyStatisticsEntry 4 }

    hwXQoSCarIfApplyStatDiscardPackets OBJECT-TYPE
        SYNTAX Counter64
        MAX-ACCESS read-only
        STATUS current
        DESCRIPTION
            "Discarded packets."
        ::= { hwXQoSCarIfApplyStatisticsEntry 5 }

    hwXQoSCarIfApplyStatDiscardBytes OBJECT-TYPE
        SYNTAX Counter64
        MAX-ACCESS read-only
        STATUS current
        DESCRIPTION
            "Discarded bytes."
        ::= { hwXQoSCarIfApplyStatisticsEntry 6 }

    hwXQoSCarIfApplyStatResetFlag OBJECT-TYPE
        SYNTAX EnabledStatus
        MAX-ACCESS read-write
        STATUS current
        DESCRIPTION
            "Reset flag enable(1),disable(2)."
        ::= { hwXQoSCarIfApplyStatisticsEntry 7 }


    hwXQoSUnicastPktsCongestionAlarmObjects OBJECT IDENTIFIER ::= { hwXQoSObjects 34 }

    hwXQoSUnicastPktsCongestionInterfaceAlarmTable OBJECT-TYPE
        SYNTAX SEQUENCE OF HwXQoSUnicastPktsCongestionInterfaceAlarmEntry
        MAX-ACCESS not-accessible
        STATUS current
        DESCRIPTION
            "hwXQoSUnicastPktsCongestionInterfaceAlarmTable"
        ::= { hwXQoSUnicastPktsCongestionAlarmObjects 1 }

    hwXQoSUnicastPktsCongestionInterfaceAlarmEntry OBJECT-TYPE
        SYNTAX HwXQoSUnicastPktsCongestionInterfaceAlarmEntry
        MAX-ACCESS not-accessible
        STATUS current
        DESCRIPTION
            "hwXQoSUnicastPktsCongestionInterfaceAlarmEntry"
        INDEX { hwXQoSUnicastPktsCongestionInterfaceAlarmIfName, hwXQoSUnicastPktsCongestionInterfaceAlarmDirection }
        ::= { hwXQoSUnicastPktsCongestionInterfaceAlarmTable 1 }

    HwXQoSUnicastPktsCongestionInterfaceAlarmEntry ::=
        SEQUENCE {
            hwXQoSUnicastPktsCongestionInterfaceAlarmIfName
                OCTET STRING,
            hwXQoSUnicastPktsCongestionInterfaceAlarmDirection
                OCTET STRING
                }

    hwXQoSUnicastPktsCongestionInterfaceAlarmIfName OBJECT-TYPE
        SYNTAX OCTET STRING
        MAX-ACCESS read-only
        STATUS current
        DESCRIPTION
            "The name of physical interface."
        ::= { hwXQoSUnicastPktsCongestionInterfaceAlarmEntry 1 }

    hwXQoSUnicastPktsCongestionInterfaceAlarmDirection OBJECT-TYPE
        SYNTAX OCTET STRING
        MAX-ACCESS read-only
        STATUS current
        DESCRIPTION
            "The direction of physical interface."
        ::= { hwXQoSUnicastPktsCongestionInterfaceAlarmEntry 2 }

--begin add by sunqirui
    hwXQoSStormControlAlarmNotification OBJECT IDENTIFIER ::= { hwXQoSObjects 35 }

    hwXQoSStormControlAlarm NOTIFICATION-TYPE
        OBJECTS { hwXQoSStormControlIfIndex, hwXQoSStormControlIfName, hwXQoSStormControlType, hwXQoSStormControlThreshold,
            hwXQoSStormControlMode, hwXQoSStormControlActionName }
        STATUS current
        DESCRIPTION
            "The SNMP trap is generated when the rate of packet exceeded the storm-control Threshold.
            hwXQoSStormControlIfIndex: The interface index, equal to ifIndex.
            hwXQoSStormControlIfName: The interface name.
            hwXQoSStormControlType: The type of storm control.
            hwXQoSStormControlThreshold: The threshold of the packets rate.
            hwXQoSStormControlMode: The mode of the packets.
            hwXQoSStormControlActionName: The storm control action."
        ::= { hwXQoSStormControlAlarmNotification 1 }


    hwXQoSStormControlAlarmResume NOTIFICATION-TYPE
        OBJECTS { hwXQoSStormControlIfIndex, hwXQoSStormControlIfName, hwXQoSStormControlType, hwXQoSStormControlThreshold,
            hwXQoSStormControlMode }
        STATUS current
        DESCRIPTION
            "The SNMP trap is generated when rate of packets is less than the storm control threshold.
            hwXQoSStormControlIfIndex: The interface index, equal to ifIndex.
            hwXQoSStormControlIfName: The interface name.
            hwXQoSStormControlType: The type of storm control.
            hwXQoSStormControlThreshold: The threshold of the packets rate.
            hwXQoSStormControlMode: The mode of the packets."
        ::= { hwXQoSStormControlAlarmNotification 2 }
--end add by sunqirui

    hwXQoSPacketsDropInterfaceAlarmObjects OBJECT IDENTIFIER ::= { hwXQoSObjects 36 }

    hwXQoSPacketsDropInterfaceAlarmTable OBJECT-TYPE
        SYNTAX SEQUENCE OF HwXQoSPacketsDropInterfaceAlarmEntry
        MAX-ACCESS not-accessible
        STATUS current
        DESCRIPTION
            "hwXQoSPacketsDropInterfaceAlarmTable"
        ::= { hwXQoSPacketsDropInterfaceAlarmObjects 1 }

    hwXQoSPacketsDropInterfaceAlarmEntry OBJECT-TYPE
        SYNTAX HwXQoSPacketsDropInterfaceAlarmEntry
        MAX-ACCESS not-accessible
        STATUS current
        DESCRIPTION
            "hwXQoSPacketsDropInterfaceAlarmEntry"
        INDEX { hwXQoSPacketsDropInterfaceAlarmIfName, hwXQoSPacketsDropInterfaceAlarmQueueId, hwXQoSPacketsDropInterfaceAlarmSlotId }
        ::= { hwXQoSPacketsDropInterfaceAlarmTable 1 }

    HwXQoSPacketsDropInterfaceAlarmEntry ::=
        SEQUENCE {
            hwXQoSPacketsDropInterfaceAlarmIfName
                OCTET STRING,
            hwXQoSPacketsDropInterfaceAlarmQueueId
                Integer32,
            hwXQoSPacketsDropInterfaceAlarmSlotId
                OCTET STRING,
            hwXQoSPacketsDropInterfaceAlarmPackets
                Counter64,
            hwXQoSPacketsDropInterfaceAlarmBytes
                Counter64
                }

    hwXQoSPacketsDropInterfaceAlarmIfName OBJECT-TYPE
        SYNTAX OCTET STRING
        MAX-ACCESS read-only
        STATUS current
        DESCRIPTION
            "The name of physical interface."
        ::= { hwXQoSPacketsDropInterfaceAlarmEntry 1 }

    hwXQoSPacketsDropInterfaceAlarmQueueId OBJECT-TYPE
        SYNTAX Integer32
        MAX-ACCESS read-only
        STATUS current
        DESCRIPTION
            "Queue Id of physical interface."
        ::= { hwXQoSPacketsDropInterfaceAlarmEntry 2 }

    hwXQoSPacketsDropInterfaceAlarmSlotId OBJECT-TYPE
        SYNTAX OCTET STRING
        MAX-ACCESS read-only
        STATUS current
        DESCRIPTION
            "Slot where packets dropped."
        ::= { hwXQoSPacketsDropInterfaceAlarmEntry 3 }

    hwXQoSPacketsDropInterfaceAlarmPackets OBJECT-TYPE
        SYNTAX Counter64
        MAX-ACCESS read-only
        STATUS current
        DESCRIPTION
            "The number of drop packets."
        ::= { hwXQoSPacketsDropInterfaceAlarmEntry 4 }

    hwXQoSPacketsDropInterfaceAlarmBytes OBJECT-TYPE
        SYNTAX Counter64
        MAX-ACCESS read-only
        STATUS current
        DESCRIPTION
            "The number of drop bytes."
        ::= { hwXQoSPacketsDropInterfaceAlarmEntry 5 }

    hwXQoSRcyPortPktsDropAlarmObjects OBJECT IDENTIFIER ::= { hwXQoSObjects 37 }

    hwXQoSRcyPortPktsDropAlarmTable OBJECT-TYPE
        SYNTAX SEQUENCE OF HwXQoSRcyPortPktsDropAlarmEntry
        MAX-ACCESS not-accessible
        STATUS current
        DESCRIPTION
            "hwXQoSRcyPortPktsDropAlarmTable"
        ::= { hwXQoSRcyPortPktsDropAlarmObjects 1 }

    hwXQoSRcyPortPktsDropAlarmEntry OBJECT-TYPE
        SYNTAX HwXQoSRcyPortPktsDropAlarmEntry
        MAX-ACCESS not-accessible
        STATUS current
        DESCRIPTION
            "hwXQoSRcyPortPktsDropAlarmEntry"
        INDEX { hwXQoSRcyPortPktsDropAlarmPortId, hwXQoSRcyPortPktsDropAlarmSlotId, hwXQoSRcyPortPktsDropAlarmChipId }
        ::= { hwXQoSRcyPortPktsDropAlarmTable 1 }

    HwXQoSRcyPortPktsDropAlarmEntry ::=
        SEQUENCE {
            hwXQoSRcyPortPktsDropAlarmPortId
                Integer32,
            hwXQoSRcyPortPktsDropAlarmSlotId
                OCTET STRING,
            hwXQoSRcyPortPktsDropAlarmChipId
                Integer32
                }

    hwXQoSRcyPortPktsDropAlarmPortId OBJECT-TYPE
        SYNTAX Integer32
        MAX-ACCESS read-only
        STATUS current
        DESCRIPTION
            "Recycle port where packets dropped."
        ::= { hwXQoSRcyPortPktsDropAlarmEntry 1 }

    hwXQoSRcyPortPktsDropAlarmSlotId OBJECT-TYPE
        SYNTAX OCTET STRING
        MAX-ACCESS read-only
        STATUS current
        DESCRIPTION
            "Slot where packets dropped."
        ::= { hwXQoSRcyPortPktsDropAlarmEntry 2 }

    hwXQoSRcyPortPktsDropAlarmChipId OBJECT-TYPE
        SYNTAX Integer32
        MAX-ACCESS read-only
        STATUS current
        DESCRIPTION
            "Chip where packets dropped."
        ::= { hwXQoSRcyPortPktsDropAlarmEntry 3 }

    hwXQoSUnicastPktsDiscardAlarmObjects OBJECT IDENTIFIER ::= { hwXQoSObjects 38 }

    hwXQoSUnicastPktsDiscardAlarmTable OBJECT-TYPE
        SYNTAX SEQUENCE OF HwXQoSUnicastPktsDiscardAlarmEntry
        MAX-ACCESS not-accessible
        STATUS current
        DESCRIPTION
            "hwXQoSUnicastPktsDiscardAlarmTable"
        ::= { hwXQoSUnicastPktsDiscardAlarmObjects 1 }

    hwXQoSUnicastPktsDiscardAlarmEntry OBJECT-TYPE
        SYNTAX HwXQoSUnicastPktsDiscardAlarmEntry
        MAX-ACCESS not-accessible
        STATUS current
        DESCRIPTION
            "hwXQoSUnicastPktsDiscardAlarmEntry"
        INDEX { hwXQoSUnicastPktsDiscardAlarmSlotid }
        ::= { hwXQoSUnicastPktsDiscardAlarmTable 1 }

    HwXQoSUnicastPktsDiscardAlarmEntry ::=
        SEQUENCE {
            hwXQoSUnicastPktsDiscardAlarmSlotid
                OCTET STRING
                }

    hwXQoSUnicastPktsDiscardAlarmSlotid OBJECT-TYPE
        SYNTAX OCTET STRING
        MAX-ACCESS read-only
        STATUS current
        DESCRIPTION
            "slot id."
        ::= { hwXQoSUnicastPktsDiscardAlarmEntry 1 }

--begin add by sunqirui, storm suppress droped alarm
    hwXQoSStormSuppressAlarmObjects OBJECT IDENTIFIER ::= { hwXQoSObjects 40 }

    hwXQoSStormSuppressAlarmTable OBJECT-TYPE
        SYNTAX SEQUENCE OF HwXQoSStormSuppressAlarmEntry
        MAX-ACCESS not-accessible
        STATUS current
        DESCRIPTION
            "A table about storm suppress configuration information."
        ::= { hwXQoSStormSuppressAlarmObjects 1 }

    hwXQoSStormSuppressAlarmEntry OBJECT-TYPE
        SYNTAX HwXQoSStormSuppressAlarmEntry
        MAX-ACCESS not-accessible
        STATUS current
        DESCRIPTION
            "hwXQoSStormSuppressAlarmEntry"
        INDEX { hwXQoSStormSuppressAlarmIfIndex}
        ::= { hwXQoSStormSuppressAlarmTable 1 }

    HwXQoSStormSuppressAlarmEntry ::=
        SEQUENCE {
            hwXQoSStormSuppressAlarmIfIndex
                InterfaceIndex,
            hwXQoSStormSuppressAlarmIfName
                OCTET STRING
                }

    hwXQoSStormSuppressAlarmIfIndex OBJECT-TYPE
        SYNTAX InterfaceIndex
        MAX-ACCESS read-only
        STATUS current
        DESCRIPTION
            "The interface index, equal to ifIndex."
        ::= { hwXQoSStormSuppressAlarmEntry 1 }

    hwXQoSStormSuppressAlarmIfName OBJECT-TYPE
        SYNTAX OCTET STRING
        MAX-ACCESS read-only
        STATUS current
        DESCRIPTION
            "The interface name."
        ::= { hwXQoSStormSuppressAlarmEntry 2 }
    hwXQoSStormSuppressSlotAlarmTable OBJECT-TYPE
        SYNTAX SEQUENCE OF HwXQoSStormSuppressSlotAlarmEntry
        MAX-ACCESS not-accessible
        STATUS current
        DESCRIPTION
            "A table about storm suppress packet alarm information by slot."
        ::= { hwXQoSStormSuppressAlarmObjects 2 }

    hwXQoSStormSuppressSlotAlarmEntry OBJECT-TYPE
        SYNTAX HwXQoSStormSuppressSlotAlarmEntry
        MAX-ACCESS not-accessible
        STATUS current
        DESCRIPTION
            "HwXQoSStormSuppressSlotAlarmEntry"
        INDEX { hwXQoSStormSuppressSlotAlarmSlot }
        ::= { hwXQoSStormSuppressSlotAlarmTable 1 }

    HwXQoSStormSuppressSlotAlarmEntry ::=
        SEQUENCE {
            hwXQoSStormSuppressSlotAlarmSlot
                OCTET STRING
                }

    hwXQoSStormSuppressSlotAlarmSlot OBJECT-TYPE
        SYNTAX OCTET STRING
        MAX-ACCESS read-only
        STATUS current
        DESCRIPTION
            "The slot."
        ::= { hwXQoSStormSuppressSlotAlarmEntry 1 }
--end add by sunqirui, storm suppress droped alarm

    hwXQoSIngressPktsDiscardAlarmObjects OBJECT IDENTIFIER ::= { hwXQoSObjects 42 }

    hwXQoSIngressPktsDiscardAlarmTable OBJECT-TYPE
        SYNTAX SEQUENCE OF HwXQoSIngressPktsDiscardAlarmEntry
        MAX-ACCESS not-accessible
        STATUS current
        DESCRIPTION
            "hwXQoSIngressPktsDiscardAlarmTable"
        ::= { hwXQoSIngressPktsDiscardAlarmObjects 1 }

    hwXQoSIngressPktsDiscardAlarmEntry OBJECT-TYPE
        SYNTAX HwXQoSIngressPktsDiscardAlarmEntry
        MAX-ACCESS not-accessible
        STATUS current
        DESCRIPTION
            "hwXQoSIngressPktsDiscardAlarmEntry"
        INDEX { hwXQoSIngressPktsDiscardAlarmSlotid }
        ::= { hwXQoSIngressPktsDiscardAlarmTable 1 }

    HwXQoSIngressPktsDiscardAlarmEntry ::=
        SEQUENCE {
            hwXQoSIngressPktsDiscardAlarmSlotid
                OCTET STRING
                }

    hwXQoSIngressPktsDiscardAlarmSlotid OBJECT-TYPE
        SYNTAX OCTET STRING
        MAX-ACCESS read-only
        STATUS current
        DESCRIPTION
            "slot id."
        ::= { hwXQoSIngressPktsDiscardAlarmEntry 1 }

    hwXQoSIngressAgingDiscardAlarmObjects OBJECT IDENTIFIER ::= { hwXQoSObjects 43 }

    hwXQoSIngressAgingDiscardAlarmTable OBJECT-TYPE
        SYNTAX SEQUENCE OF HwXQoSIngressAgingDiscardAlarmEntry
        MAX-ACCESS not-accessible
        STATUS current
        DESCRIPTION
            "hwXQoSIngressAgingDiscardAlarmTable"
        ::= { hwXQoSIngressAgingDiscardAlarmObjects 1 }

    hwXQoSIngressAgingDiscardAlarmEntry OBJECT-TYPE
        SYNTAX HwXQoSIngressAgingDiscardAlarmEntry
        MAX-ACCESS not-accessible
        STATUS current
        DESCRIPTION
            "hwXQoSIngressAgingDiscardAlarmEntry"
        INDEX { hwXQoSIngressAgingDiscardAlarmSlotid }
        ::= { hwXQoSIngressAgingDiscardAlarmTable 1 }

    HwXQoSIngressAgingDiscardAlarmEntry ::=
        SEQUENCE {
            hwXQoSIngressAgingDiscardAlarmSlotid
                OCTET STRING
                }

    hwXQoSIngressAgingDiscardAlarmSlotid OBJECT-TYPE
        SYNTAX OCTET STRING
        MAX-ACCESS read-only
        STATUS current
        DESCRIPTION
            "slot id."
        ::= { hwXQoSIngressAgingDiscardAlarmEntry 1 }

    hwXQoSIfCarDiscardAlarmObjects OBJECT IDENTIFIER ::= { hwXQoSObjects 44 }

    hwXQoSIfCarDiscardAlarmTable OBJECT-TYPE
        SYNTAX SEQUENCE OF HwXQoSIfCarDiscardAlarmEntry
        MAX-ACCESS not-accessible
        STATUS current
        DESCRIPTION
            "hwXQoSIfCarDiscardAlarmTable"
        ::= { hwXQoSIfCarDiscardAlarmObjects 1 }

    hwXQoSIfCarDiscardAlarmEntry OBJECT-TYPE
        SYNTAX HwXQoSIfCarDiscardAlarmEntry
        MAX-ACCESS not-accessible
        STATUS current
        DESCRIPTION
            "hwXQoSIfCarDiscardAlarmEntry"
        INDEX { hwXQoSIfCarDiscardAlarmSlotid, hwXQoSIfCarDiscardAlarmIfName, hwXQoSIfCarDiscardAlarmDirection }
        ::= { hwXQoSIfCarDiscardAlarmTable 1 }

    HwXQoSIfCarDiscardAlarmEntry ::=
        SEQUENCE {
            hwXQoSIfCarDiscardAlarmSlotid
                OCTET STRING,
            hwXQoSIfCarDiscardAlarmIfName
                OCTET STRING,
            hwXQoSIfCarDiscardAlarmDirection
                OCTET STRING
                }

    hwXQoSIfCarDiscardAlarmSlotid OBJECT-TYPE
        SYNTAX OCTET STRING
        MAX-ACCESS read-only
        STATUS current
        DESCRIPTION
            "slot id."
        ::= { hwXQoSIfCarDiscardAlarmEntry 1 }

    hwXQoSIfCarDiscardAlarmIfName OBJECT-TYPE
        SYNTAX OCTET STRING
        MAX-ACCESS read-only
        STATUS current
        DESCRIPTION
            "interface name."
        ::= { hwXQoSIfCarDiscardAlarmEntry 2 }

    hwXQoSIfCarDiscardAlarmDirection OBJECT-TYPE
        SYNTAX OCTET STRING
        MAX-ACCESS read-only
        STATUS current
        DESCRIPTION
            "interface car direction."
        ::= { hwXQoSIfCarDiscardAlarmEntry 3 }


--begin add by guzhen
    hwXQoSRedirectNextHopInvalidAlarmObjects OBJECT IDENTIFIER ::= { hwXQoSObjects 48 }

    hwXQoSRedirectNextHopInvalidAlarmTable OBJECT-TYPE
        SYNTAX SEQUENCE OF HwXQoSRedirectNextHopInvalidAlarmEntry
        MAX-ACCESS not-accessible
        STATUS current
        DESCRIPTION
            "It will alarm when the redirect nexthop address did not match the network segment of the outbound interface."
        ::= { hwXQoSRedirectNextHopInvalidAlarmObjects 1 }

    hwXQoSRedirectNextHopInvalidAlarmEntry OBJECT-TYPE
        SYNTAX HwXQoSRedirectNextHopInvalidAlarmEntry
        MAX-ACCESS not-accessible
        STATUS current
        DESCRIPTION
            "It will alarm when the redirect nexthop address did not match the network segment of the outbound interface."
        INDEX { hwXQoSRedirectNextHopInvalidAlarmBehaviorName, hwXQoSRedirectNextHopInvalidAlarmRdrType, hwXQoSRedirectNextHopInvalidAlarmInterface }
        ::= { hwXQoSRedirectNextHopInvalidAlarmTable 1 }

    HwXQoSRedirectNextHopInvalidAlarmEntry ::=
        SEQUENCE {
            hwXQoSRedirectNextHopInvalidAlarmBehaviorName
                OCTET STRING,
            hwXQoSRedirectNextHopInvalidAlarmRdrType
                Integer32,
            hwXQoSRedirectNextHopInvalidAlarmInterface
                OCTET STRING
            }

    hwXQoSRedirectNextHopInvalidAlarmBehaviorName OBJECT-TYPE
        SYNTAX OCTET STRING (SIZE (1..128))
        MAX-ACCESS read-only
        STATUS current
        DESCRIPTION
            "Behavior ID of the Behavior when the redirect nexthop address did not match the network segment of the outbound interface."
         ::= { hwXQoSRedirectNextHopInvalidAlarmEntry 1 }

    hwXQoSRedirectNextHopInvalidAlarmRdrType OBJECT-TYPE
        SYNTAX Integer32 (0..2)
        MAX-ACCESS read-only
        STATUS current
        DESCRIPTION
            "Redirect type the Behavior when the redirect nexthop address did not match the network segment of the outbound interface."
        ::= { hwXQoSRedirectNextHopInvalidAlarmEntry 2 }

    hwXQoSRedirectNextHopInvalidAlarmInterface OBJECT-TYPE
        SYNTAX OCTET STRING (SIZE (1..128))
        MAX-ACCESS read-only
        STATUS current
        DESCRIPTION
            "Name of the interface when the redirect nexthop address did not match the network segment of the outbound interface."
         ::= { hwXQoSRedirectNextHopInvalidAlarmEntry 3 }
--end add by guzhen

--begin add by yangting
    hwXQoSRedirectNextHopLackResAlarmTable OBJECT-TYPE
        SYNTAX SEQUENCE OF HwXQoSRedirectNextHopLackResAlarmEntry
        MAX-ACCESS not-accessible
        STATUS current
        DESCRIPTION
            "It will alarm when the redirecting traffic to the next hop is invalid due to insufficient NHP resources."
         ::= { hwXQoSRedirectNextHopInvalidAlarmObjects 2 }

    hwXQoSRedirectNextHopLackResAlarmEntry OBJECT-TYPE
        SYNTAX HwXQoSRedirectNextHopLackResAlarmEntry
        MAX-ACCESS not-accessible
        STATUS current
        DESCRIPTION
            "It will alarm when the redirecting traffic to the next hop is invalid due to insufficient NHP resources."
        INDEX { hwXQoSRedirectNextHopLackResAlarmBehaviorName, hwXQoSRedirectNextHopLackResAlarmSlotID, hwXQoSRedirectNextHopLackResAlarmRdrType }
         ::= { hwXQoSRedirectNextHopLackResAlarmTable 1 }

        HwXQoSRedirectNextHopLackResAlarmEntry ::=
        SEQUENCE {
                hwXQoSRedirectNextHopLackResAlarmBehaviorName
                    OCTET STRING,
                hwXQoSRedirectNextHopLackResAlarmSlotID
                    OCTET STRING,
                hwXQoSRedirectNextHopLackResAlarmRdrType
                    Integer32
            }

    hwXQoSRedirectNextHopLackResAlarmBehaviorName OBJECT-TYPE
        SYNTAX OCTET STRING (SIZE (1..128))
        MAX-ACCESS read-only
        STATUS current
        DESCRIPTION
            "Behavior ID of the Behavior when the redirecting traffic to the next hop is invalid due to insufficient NHP resources."
        ::= { hwXQoSRedirectNextHopLackResAlarmEntry 1 }

    hwXQoSRedirectNextHopLackResAlarmSlotID OBJECT-TYPE
        SYNTAX OCTET STRING
        MAX-ACCESS read-only
        STATUS current
        DESCRIPTION
            "slot id."
        ::= { hwXQoSRedirectNextHopLackResAlarmEntry 2 }

    hwXQoSRedirectNextHopLackResAlarmRdrType OBJECT-TYPE
        SYNTAX Integer32 (0..2)
        MAX-ACCESS read-only
        STATUS current
        DESCRIPTION
            "Redirect type the Behavior when the redirecting traffic to the next hop is invalid due to insufficient NHP resources."
        ::= { hwXQoSRedirectNextHopLackResAlarmEntry 3 }
--end add by yangting

    hwXQosQueueExcepAlarmObjects OBJECT IDENTIFIER ::= { hwXQoSObjects 45 }

    hwXQosQueueExcepAlarmTable OBJECT-TYPE
        SYNTAX SEQUENCE OF HwXQosQueueExcepAlarmEntry
        MAX-ACCESS not-accessible
        STATUS current
        DESCRIPTION
            "hwXQosQueueExcepAlarmTable"
        ::= { hwXQosQueueExcepAlarmObjects 1 }

    hwXQosQueueExcepAlarmEntry OBJECT-TYPE
        SYNTAX HwXQosQueueExcepAlarmEntry
        MAX-ACCESS not-accessible
        STATUS current
        DESCRIPTION
            "hwXQosQueueExcepAlarmEntry"
        INDEX { hwXQosQueueExcepAlarmSlotId, hwXQosQueueExcepAlarmProtocal }
        ::= { hwXQosQueueExcepAlarmTable 1 }

    HwXQosQueueExcepAlarmEntry ::=
        SEQUENCE {
            hwXQosQueueExcepAlarmSlotId
                OCTET STRING,
            hwXQosQueueExcepAlarmProtocal
                OCTET STRING
                }

    hwXQosQueueExcepAlarmSlotId OBJECT-TYPE
        SYNTAX OCTET STRING
        MAX-ACCESS read-only
        STATUS current
        DESCRIPTION
            "slot id."
        ::= { hwXQosQueueExcepAlarmEntry 1 }
    hwXQosQueueExcepAlarmProtocal OBJECT-TYPE
        SYNTAX OCTET STRING
        MAX-ACCESS read-only
        STATUS current
        DESCRIPTION
            "protocal."
        ::= { hwXQosQueueExcepAlarmEntry 2 }

    hwXACLFEIMemoryFullAlarmObjects OBJECT IDENTIFIER ::= { hwXQoSObjects 46 }

    hwXACLFEIMemoryFullAlarmTable OBJECT-TYPE
        SYNTAX SEQUENCE OF HwXACLFEIMemoryFullAlarmEntry
        MAX-ACCESS not-accessible
        STATUS current
        DESCRIPTION
            "hwXACLFEIMemoryFullAlarmTable"
        ::= { hwXACLFEIMemoryFullAlarmObjects 1 }

    hwXACLFEIMemoryFullAlarmEntry OBJECT-TYPE
        SYNTAX HwXACLFEIMemoryFullAlarmEntry
        MAX-ACCESS not-accessible
        STATUS current
        DESCRIPTION
            "hwXACLFEIMemoryFullAlarmEntry"
        INDEX { hwXACLFEIMemoryFullAlarmSlotid }
        ::= { hwXACLFEIMemoryFullAlarmTable 1 }

    HwXACLFEIMemoryFullAlarmEntry ::=
        SEQUENCE {
            hwXACLFEIMemoryFullAlarmSlotid
                OCTET STRING
                }

    hwXACLFEIMemoryFullAlarmSlotid OBJECT-TYPE
        SYNTAX OCTET STRING
        MAX-ACCESS read-only
        STATUS current
        DESCRIPTION
            "slot id."
        ::= { hwXACLFEIMemoryFullAlarmEntry 1 }

    hwXQoSPfcTurnOffAlarmObjects OBJECT IDENTIFIER ::= { hwXQoSObjects 49 }

    hwXQoSPfcTurnOffAlarmTable OBJECT-TYPE
        SYNTAX SEQUENCE OF HwXQoSPfcTurnOffAlarmEntry
        MAX-ACCESS not-accessible
        STATUS current
        DESCRIPTION
            "hwXQoSPfcTurnOffAlarmTable"
        ::= { hwXQoSPfcTurnOffAlarmObjects 1 }

    hwXQoSPfcTurnOffAlarmEntry OBJECT-TYPE
        SYNTAX HwXQoSPfcTurnOffAlarmEntry
        MAX-ACCESS not-accessible
        STATUS current
        DESCRIPTION
            "hwXQoSPfcTurnOffAlarmEntry"
        INDEX { hwXQoSPfcTurnOffAlarmIfName, hwXQoSPfcTurnOffAlarmPriority}
        ::= { hwXQoSPfcTurnOffAlarmTable 1 }

    HwXQoSPfcTurnOffAlarmEntry ::=
        SEQUENCE {
            hwXQoSPfcTurnOffAlarmIfName
                OCTET STRING,
            hwXQoSPfcTurnOffAlarmPriority
                Integer32,
            hwXQoSPfcTurnOffAlarmDetectedNumber
                Integer32,
            hwXQoSPfcTurnOffAlarmThreshold
                Integer32
                }

    hwXQoSPfcTurnOffAlarmIfName OBJECT-TYPE
        SYNTAX OCTET STRING
        MAX-ACCESS accessible-for-notify
        STATUS current
        DESCRIPTION
            "ifname."
        ::= { hwXQoSPfcTurnOffAlarmEntry 1 }
    hwXQoSPfcTurnOffAlarmPriority OBJECT-TYPE
        SYNTAX Integer32
        MAX-ACCESS accessible-for-notify
        STATUS current
        DESCRIPTION
            "priority."
        ::= { hwXQoSPfcTurnOffAlarmEntry 2 }
    hwXQoSPfcTurnOffAlarmDetectedNumber OBJECT-TYPE
        SYNTAX Integer32
        MAX-ACCESS accessible-for-notify
        STATUS current
        DESCRIPTION
            "detect number."
        ::= { hwXQoSPfcTurnOffAlarmEntry 3 }
    hwXQoSPfcTurnOffAlarmThreshold OBJECT-TYPE
        SYNTAX Integer32
        MAX-ACCESS accessible-for-notify
        STATUS current
        DESCRIPTION
            "threshold."
        ::= { hwXQoSPfcTurnOffAlarmEntry 4 }


    hwXQoSModuleAlarmPatchStubObjects OBJECT IDENTIFIER ::= { hwXQoSObjects 120 }

    hwXQoSModuleAlarmPatchStubTable OBJECT-TYPE
        SYNTAX SEQUENCE OF HwXQoSModuleAlarmPatchStubEntry
        MAX-ACCESS not-accessible
        STATUS current
        DESCRIPTION
            "hwXQoSModuleAlarmPatchStubTable"
        ::= { hwXQoSModuleAlarmPatchStubObjects 1 }

    hwXQoSModuleAlarmPatchStubEntry OBJECT-TYPE
        SYNTAX HwXQoSModuleAlarmPatchStubEntry
        MAX-ACCESS not-accessible
        STATUS current
        DESCRIPTION
            "hwXQoSModuleAlarmPatchStubEntry"
        INDEX { hwXQoSModuleAlarmPatchStubModule }
        ::= { hwXQoSModuleAlarmPatchStubTable 1 }

    HwXQoSModuleAlarmPatchStubEntry ::=
        SEQUENCE {
            hwXQoSModuleAlarmPatchStubModule
                OCTET STRING
                }

    hwXQoSModuleAlarmPatchStubModule OBJECT-TYPE
        SYNTAX OCTET STRING
        MAX-ACCESS accessible-for-notify
        STATUS current
        DESCRIPTION
            "module."
        ::= { hwXQoSModuleAlarmPatchStubEntry 1 }

    hwXQoSSlotAlarmPatchStubObjects OBJECT IDENTIFIER ::= { hwXQoSObjects 122 }

    hwXQoSSlotAlarmPatchStubTable OBJECT-TYPE
        SYNTAX SEQUENCE OF HwXQoSSlotAlarmPatchStubEntry
        MAX-ACCESS not-accessible
        STATUS current
        DESCRIPTION
            "hwXQoSSlotAlarmPatchStubTable"
        ::= { hwXQoSSlotAlarmPatchStubObjects 1 }

    hwXQoSSlotAlarmPatchStubEntry OBJECT-TYPE
        SYNTAX HwXQoSSlotAlarmPatchStubEntry
        MAX-ACCESS not-accessible
        STATUS current
        DESCRIPTION
            "hwXQoSSlotAlarmPatchStubEntry"
        INDEX { hwXQoSSlotAlarmPatchStubModule }
        ::= { hwXQoSSlotAlarmPatchStubTable 1 }

    HwXQoSSlotAlarmPatchStubEntry ::=
        SEQUENCE {
            hwXQoSSlotAlarmPatchStubModule
                OCTET STRING
                }

    hwXQoSSlotAlarmPatchStubModule OBJECT-TYPE
        SYNTAX OCTET STRING
        MAX-ACCESS accessible-for-notify
        STATUS current
        DESCRIPTION
            "module."
        ::= { hwXQoSSlotAlarmPatchStubEntry 1 }

    hwXQoSDevAlarmPatchStubObjects OBJECT IDENTIFIER ::= { hwXQoSObjects 124 }

    hwXQoSDevAlarmPatchStubTable OBJECT-TYPE
        SYNTAX SEQUENCE OF HwXQoSDevAlarmPatchStubEntry
        MAX-ACCESS not-accessible
        STATUS current
        DESCRIPTION
            "hwXQoSDevAlarmPatchStubTable"
        ::= { hwXQoSDevAlarmPatchStubObjects 1 }

    hwXQoSDevAlarmPatchStubEntry OBJECT-TYPE
        SYNTAX HwXQoSDevAlarmPatchStubEntry
        MAX-ACCESS not-accessible
        STATUS current
        DESCRIPTION
            "hwXQoSDevAlarmPatchStubEntry"
        INDEX { hwXQoSDevAlarmPatchStubModule }
        ::= { hwXQoSDevAlarmPatchStubTable 1 }

    HwXQoSDevAlarmPatchStubEntry ::=
        SEQUENCE {
            hwXQoSDevAlarmPatchStubModule
                OCTET STRING
                }

    hwXQoSDevAlarmPatchStubModule OBJECT-TYPE
        SYNTAX OCTET STRING
        MAX-ACCESS accessible-for-notify
        STATUS current
        DESCRIPTION
            "module."
        ::= { hwXQoSDevAlarmPatchStubEntry 1 }

    hwXQoSOutPfcTurnOffAlarmObjects OBJECT IDENTIFIER ::= { hwXQoSObjects 115 }

    hwXQoSOutPfcTurnOffAlarmTable OBJECT-TYPE
        SYNTAX SEQUENCE OF HwXQoSOutPfcTurnOffAlarmEntry
        MAX-ACCESS not-accessible
        STATUS current
        DESCRIPTION
            "hwXQoSOutPfcTurnOffAlarmTable"
        ::= { hwXQoSOutPfcTurnOffAlarmObjects 1 }

    hwXQoSOutPfcTurnOffAlarmEntry OBJECT-TYPE
        SYNTAX HwXQoSOutPfcTurnOffAlarmEntry
        MAX-ACCESS not-accessible
        STATUS current
        DESCRIPTION
            "hwXQoSOutPfcTurnOffAlarmEntry"
        INDEX { hwXQoSOutPfcTurnOffAlarmIfName, hwXQoSOutPfcTurnOffAlarmPriority}
        ::= { hwXQoSOutPfcTurnOffAlarmTable 1 }

    HwXQoSOutPfcTurnOffAlarmEntry ::=
        SEQUENCE {
            hwXQoSOutPfcTurnOffAlarmIfName
                OCTET STRING,
            hwXQoSOutPfcTurnOffAlarmPriority
                Integer32,
            hwXQoSOutPfcTurnOffAlarmDetectedNumber
                Integer32,
            hwXQoSOutPfcTurnOffAlarmBuffUsage
                Integer32,
            hwXQoSOutPfcTurnOffAlarmThreshold
                Integer32
                }

    hwXQoSOutPfcTurnOffAlarmIfName OBJECT-TYPE
        SYNTAX OCTET STRING
        MAX-ACCESS accessible-for-notify
        STATUS current
        DESCRIPTION
            "ifname."
        ::= { hwXQoSOutPfcTurnOffAlarmEntry 1 }
    hwXQoSOutPfcTurnOffAlarmPriority OBJECT-TYPE
        SYNTAX Integer32
        MAX-ACCESS accessible-for-notify
        STATUS current
        DESCRIPTION
            "priority."
        ::= { hwXQoSOutPfcTurnOffAlarmEntry 2 }
    hwXQoSOutPfcTurnOffAlarmDetectedNumber OBJECT-TYPE
        SYNTAX Integer32
        MAX-ACCESS accessible-for-notify
        STATUS current
        DESCRIPTION
            "detect number."
        ::= { hwXQoSOutPfcTurnOffAlarmEntry 3 }
    hwXQoSOutPfcTurnOffAlarmBuffUsage OBJECT-TYPE
        SYNTAX Integer32
        MAX-ACCESS accessible-for-notify
        STATUS current
        DESCRIPTION
            "queue buff usage."
        ::= { hwXQoSOutPfcTurnOffAlarmEntry 4 }
    hwXQoSOutPfcTurnOffAlarmThreshold OBJECT-TYPE
        SYNTAX Integer32
        MAX-ACCESS accessible-for-notify
        STATUS current
        DESCRIPTION
            "threshold."
        ::= { hwXQoSOutPfcTurnOffAlarmEntry 5 }

    hwXQoSPfcTurnOffResumeObjects OBJECT IDENTIFIER ::= { hwXQoSObjects 51 }

    hwXQoSPfcTurnOffResumeTable OBJECT-TYPE
        SYNTAX SEQUENCE OF HwXQoSPfcTurnOffResumeEntry
        MAX-ACCESS not-accessible
        STATUS current
        DESCRIPTION
            "hwXQoSPfcTurnOffResumeTable"
        ::= { hwXQoSPfcTurnOffResumeObjects 1 }

    hwXQoSPfcTurnOffResumeEntry OBJECT-TYPE
        SYNTAX HwXQoSPfcTurnOffResumeEntry
        MAX-ACCESS not-accessible
        STATUS current
        DESCRIPTION
            "hwXQoSPfcTurnOffResumeEntry"
        INDEX { hwXQoSPfcTurnOffResumeIfName, hwXQoSPfcTurnOffResumePriority }
        ::= { hwXQoSPfcTurnOffResumeTable 1 }

    HwXQoSPfcTurnOffResumeEntry ::=
        SEQUENCE {
            hwXQoSPfcTurnOffResumeIfName
                OCTET STRING,
            hwXQoSPfcTurnOffResumePriority
                Integer32
                }

    hwXQoSPfcTurnOffResumeIfName OBJECT-TYPE
        SYNTAX OCTET STRING
        MAX-ACCESS accessible-for-notify
        STATUS current
        DESCRIPTION
            "ifname."
        ::= { hwXQoSPfcTurnOffResumeEntry 1 }
    hwXQoSPfcTurnOffResumePriority OBJECT-TYPE
        SYNTAX Integer32
        MAX-ACCESS accessible-for-notify
        STATUS current
        DESCRIPTION
            "priority."
        ::= { hwXQoSPfcTurnOffResumeEntry 2 }

    hwXQoSModuleAlarmPatchStubResumeObjects OBJECT IDENTIFIER ::= { hwXQoSObjects 121 }

    hwXQoSModuleAlarmPatchStubResumeTable OBJECT-TYPE
        SYNTAX SEQUENCE OF HwXQoSModuleAlarmPatchStubResumeEntry
        MAX-ACCESS not-accessible
        STATUS current
        DESCRIPTION
            "hwXQoSModuleAlarmPatchStubResumeTable"
        ::= { hwXQoSModuleAlarmPatchStubResumeObjects 1 }

    hwXQoSModuleAlarmPatchStubResumeEntry OBJECT-TYPE
        SYNTAX HwXQoSModuleAlarmPatchStubResumeEntry
        MAX-ACCESS not-accessible
        STATUS current
        DESCRIPTION
            "hwXQoSModuleAlarmPatchStubResumeEntry"
        INDEX { hwXQoSModuleAlarmPatchStubResumeModule }
        ::= { hwXQoSModuleAlarmPatchStubResumeTable 1 }

    HwXQoSModuleAlarmPatchStubResumeEntry ::=
        SEQUENCE {
            hwXQoSModuleAlarmPatchStubResumeModule
                OCTET STRING
                }

    hwXQoSModuleAlarmPatchStubResumeModule OBJECT-TYPE
        SYNTAX OCTET STRING
        MAX-ACCESS accessible-for-notify
        STATUS current
        DESCRIPTION
            "module."
        ::= { hwXQoSModuleAlarmPatchStubResumeEntry 1 }

    hwXQoSSlotAlarmPatchStubResumeObjects OBJECT IDENTIFIER ::= { hwXQoSObjects 123 }

    hwXQoSSlotAlarmPatchStubResumeTable OBJECT-TYPE
        SYNTAX SEQUENCE OF HwXQoSSlotAlarmPatchStubResumeEntry
        MAX-ACCESS not-accessible
        STATUS current
        DESCRIPTION
            "hwXQoSSlotAlarmPatchStubResumeTable"
        ::= { hwXQoSSlotAlarmPatchStubResumeObjects 1 }

    hwXQoSSlotAlarmPatchStubResumeEntry OBJECT-TYPE
        SYNTAX HwXQoSSlotAlarmPatchStubResumeEntry
        MAX-ACCESS not-accessible
        STATUS current
        DESCRIPTION
            "hwXQoSSlotAlarmPatchStubResumeEntry"
        INDEX { hwXQoSSlotAlarmPatchStubResumeModule }
        ::= { hwXQoSSlotAlarmPatchStubResumeTable 1 }

    HwXQoSSlotAlarmPatchStubResumeEntry ::=
        SEQUENCE {
            hwXQoSSlotAlarmPatchStubResumeModule
                OCTET STRING
                }

    hwXQoSSlotAlarmPatchStubResumeModule OBJECT-TYPE
        SYNTAX OCTET STRING
        MAX-ACCESS accessible-for-notify
        STATUS current
        DESCRIPTION
            "module."
        ::= { hwXQoSSlotAlarmPatchStubResumeEntry 1 }

    hwXQoSDevAlarmPatchStubResumeObjects OBJECT IDENTIFIER ::= { hwXQoSObjects 125 }

    hwXQoSDevAlarmPatchStubResumeTable OBJECT-TYPE
        SYNTAX SEQUENCE OF HwXQoSDevAlarmPatchStubResumeEntry
        MAX-ACCESS not-accessible
        STATUS current
        DESCRIPTION
            "hwXQoSDevAlarmPatchStubResumeTable"
        ::= { hwXQoSDevAlarmPatchStubResumeObjects 1 }

    hwXQoSDevAlarmPatchStubResumeEntry OBJECT-TYPE
        SYNTAX HwXQoSDevAlarmPatchStubResumeEntry
        MAX-ACCESS not-accessible
        STATUS current
        DESCRIPTION
            "hwXQoSDevAlarmPatchStubResumeEntry"
        INDEX { hwXQoSDevAlarmPatchStubResumeModule }
        ::= { hwXQoSDevAlarmPatchStubResumeTable 1 }

    HwXQoSDevAlarmPatchStubResumeEntry ::=
        SEQUENCE {
            hwXQoSDevAlarmPatchStubResumeModule
                OCTET STRING
                }

    hwXQoSDevAlarmPatchStubResumeModule OBJECT-TYPE
        SYNTAX OCTET STRING
        MAX-ACCESS accessible-for-notify
        STATUS current
        DESCRIPTION
            "module."
        ::= { hwXQoSDevAlarmPatchStubResumeEntry 1 }

    hwXQoSOutPfcTurnOffResumeObjects OBJECT IDENTIFIER ::= { hwXQoSObjects 116 }

    hwXQoSOutPfcTurnOffResumeTable OBJECT-TYPE
        SYNTAX SEQUENCE OF HwXQoSOutPfcTurnOffResumeEntry
        MAX-ACCESS not-accessible
        STATUS current
        DESCRIPTION
            "hwXQoSOutPfcTurnOffResumeTable"
        ::= { hwXQoSOutPfcTurnOffResumeObjects 1 }

    hwXQoSOutPfcTurnOffResumeEntry OBJECT-TYPE
        SYNTAX HwXQoSOutPfcTurnOffResumeEntry
        MAX-ACCESS not-accessible
        STATUS current
        DESCRIPTION
            "hwXQoSOutPfcTurnOffResumeEntry"
        INDEX { hwXQoSOutPfcTurnOffResumeIfName, hwXQoSOutPfcTurnOffResumePriority }
        ::= { hwXQoSOutPfcTurnOffResumeTable 1 }

    HwXQoSOutPfcTurnOffResumeEntry ::=
        SEQUENCE {
            hwXQoSOutPfcTurnOffResumeIfName
                OCTET STRING,
            hwXQoSOutPfcTurnOffResumePriority
                Integer32
                }

    hwXQoSOutPfcTurnOffResumeIfName OBJECT-TYPE
        SYNTAX OCTET STRING
        MAX-ACCESS accessible-for-notify
        STATUS current
        DESCRIPTION
            "ifname."
        ::= { hwXQoSOutPfcTurnOffResumeEntry 1 }
    hwXQoSOutPfcTurnOffResumePriority OBJECT-TYPE
        SYNTAX Integer32
        MAX-ACCESS accessible-for-notify
        STATUS current
        DESCRIPTION
            "priority."
        ::= { hwXQoSOutPfcTurnOffResumeEntry 2 }

    hwXQoSPfcDeadLockAlarmObjects OBJECT IDENTIFIER ::= { hwXQoSObjects 53 }

    hwXQoSPfcDeadLockAlarmTable OBJECT-TYPE
        SYNTAX SEQUENCE OF HwXQoSPfcDeadLockAlarmEntry
        MAX-ACCESS not-accessible
        STATUS current
        DESCRIPTION
            "hwXQoSPfcDeadLockAlarmTable"
        ::= { hwXQoSPfcDeadLockAlarmObjects 1 }

    hwXQoSPfcDeadLockAlarmEntry OBJECT-TYPE
        SYNTAX HwXQoSPfcDeadLockAlarmEntry
        MAX-ACCESS not-accessible
        STATUS current
        DESCRIPTION
            "hwXQoSPfcDeadLockAlarmEntry"
        INDEX { hwXQoSPfcDeadLockAlarmIfName, hwXQoSPfcDeadLockAlarmPriority }
        ::= { hwXQoSPfcDeadLockAlarmTable 1 }

    HwXQoSPfcDeadLockAlarmEntry ::=
        SEQUENCE {
            hwXQoSPfcDeadLockAlarmIfName
                OCTET STRING,
            hwXQoSPfcDeadLockAlarmPriority
                Integer32,
            hwXQoSPfcDeadLockAlarmDetectedNumber
                Integer32,
            hwXQoSPfcDeadLockAlarmRecoveredNumber
                Integer32
                }

    hwXQoSPfcDeadLockAlarmIfName OBJECT-TYPE
        SYNTAX OCTET STRING
        MAX-ACCESS accessible-for-notify
        STATUS current
        DESCRIPTION
            "ifname."
        ::= { hwXQoSPfcDeadLockAlarmEntry 1 }
    hwXQoSPfcDeadLockAlarmPriority OBJECT-TYPE
        SYNTAX Integer32
        MAX-ACCESS accessible-for-notify
        STATUS current
        DESCRIPTION
            "priority."
        ::= { hwXQoSPfcDeadLockAlarmEntry 2 }
    hwXQoSPfcDeadLockAlarmDetectedNumber OBJECT-TYPE
        SYNTAX Integer32
        MAX-ACCESS accessible-for-notify
        STATUS current
        DESCRIPTION
            "detect number."
        ::= { hwXQoSPfcDeadLockAlarmEntry 3 }
    hwXQoSPfcDeadLockAlarmRecoveredNumber OBJECT-TYPE
        SYNTAX Integer32
        MAX-ACCESS accessible-for-notify
        STATUS current
        DESCRIPTION
            "threshold."
        ::= { hwXQoSPfcDeadLockAlarmEntry 4 }

    hwXQoSPfcDeadLockResumeObjects OBJECT IDENTIFIER ::= { hwXQoSObjects 55 }

    hwXQoSPfcDeadLockResumeTable OBJECT-TYPE
        SYNTAX SEQUENCE OF HwXQoSPfcDeadLockResumeEntry
        MAX-ACCESS not-accessible
        STATUS current
        DESCRIPTION
            "hwXQoSPfcDeadLockResumeTable"
        ::= { hwXQoSPfcDeadLockResumeObjects 1 }

    hwXQoSPfcDeadLockResumeEntry OBJECT-TYPE
        SYNTAX HwXQoSPfcDeadLockResumeEntry
        MAX-ACCESS not-accessible
        STATUS current
        DESCRIPTION
            "hwXQoSPfcDeadLockResumeEntry"
        INDEX { hwXQoSPfcDeadLockResumeIfName, hwXQoSPfcDeadLockResumePriority }
        ::= { hwXQoSPfcDeadLockResumeTable 1 }

    HwXQoSPfcDeadLockResumeEntry ::=
        SEQUENCE {
            hwXQoSPfcDeadLockResumeIfName
                OCTET STRING,
            hwXQoSPfcDeadLockResumePriority
                Integer32
                }

    hwXQoSPfcDeadLockResumeIfName OBJECT-TYPE
        SYNTAX OCTET STRING
        MAX-ACCESS accessible-for-notify
        STATUS current
        DESCRIPTION
            "ifname."
        ::= { hwXQoSPfcDeadLockResumeEntry 1 }
    hwXQoSPfcDeadLockResumePriority OBJECT-TYPE
        SYNTAX Integer32
        MAX-ACCESS accessible-for-notify
        STATUS current
        DESCRIPTION
            "priority."
        ::= { hwXQoSPfcDeadLockResumeEntry 2 }


    hwXQoSQueueStatisticsMulticastObjects OBJECT IDENTIFIER ::= { hwXQoSObjects 56 }


    hwXQoSQueueStatisticsMulticastTable OBJECT-TYPE
        SYNTAX SEQUENCE OF HwXQoSQueueStatisticsMulticastEntry
        MAX-ACCESS not-accessible
        STATUS current
        DESCRIPTION
            "A table about multicast packets statistics of queue."
        ::= { hwXQoSQueueStatisticsMulticastObjects 1 }


    hwXQoSQueueStatisticsMulticastEntry OBJECT-TYPE
        SYNTAX HwXQoSQueueStatisticsMulticastEntry
        MAX-ACCESS not-accessible
        STATUS current
        DESCRIPTION
            "The entry about multicast packets statistics of queue."
        INDEX { hwXQoSQueueStatisticsMulticastIfIndex, hwXQoSQueueStatisticsMulticastQueueId }
        ::= { hwXQoSQueueStatisticsMulticastTable 1 }


    HwXQoSQueueStatisticsMulticastEntry ::=
        SEQUENCE {
            hwXQoSQueueStatisticsMulticastIfIndex
                Integer32,
            hwXQoSQueueStatisticsMulticastQueueId
                Integer32,
            hwXQoSQueueStatisticsMulticastPassPkts
                Counter64,
            hwXQoSQueueStatisticsMulticastPassBytes
                Counter64,
            hwXQoSQueueStatisticsMulticastPassPktsRate
                Counter64,
            hwXQoSQueueStatisticsMulticastPassBytesRate
                Counter64,
            hwXQoSQueueStatisticsMulticastDropPkts
                Counter64,
            hwXQoSQueueStatisticsMulticastDropBytes
                Counter64,
            hwXQoSQueueStatisticsMulticastDropPktsRate
                Counter64,
            hwXQoSQueueStatisticsMulticastDropBytesRate
                Counter64
            }

    hwXQoSQueueStatisticsMulticastIfIndex OBJECT-TYPE
        SYNTAX Integer32
        MAX-ACCESS not-accessible
        STATUS current
        DESCRIPTION
            "The interface index."
        ::= { hwXQoSQueueStatisticsMulticastEntry 1 }


    hwXQoSQueueStatisticsMulticastQueueId OBJECT-TYPE
        SYNTAX Integer32
        MAX-ACCESS not-accessible
        STATUS current
        DESCRIPTION
            "The queue index."
        ::= { hwXQoSQueueStatisticsMulticastEntry 2 }

    hwXQoSQueueStatisticsMulticastPassPkts OBJECT-TYPE
        SYNTAX Counter64
        MAX-ACCESS read-only
        STATUS current
        DESCRIPTION
            "The passed packets count of the queue."
        ::= { hwXQoSQueueStatisticsMulticastEntry 3 }

    hwXQoSQueueStatisticsMulticastPassBytes OBJECT-TYPE
        SYNTAX Counter64
        MAX-ACCESS read-only
        STATUS current
        DESCRIPTION
            "The passed Bytes count of the queue."
        ::= { hwXQoSQueueStatisticsMulticastEntry 4 }

    hwXQoSQueueStatisticsMulticastPassPktsRate OBJECT-TYPE
        SYNTAX Counter64
        MAX-ACCESS read-only
        STATUS current
        DESCRIPTION
            "The passed packets rate of the queue."
        ::= { hwXQoSQueueStatisticsMulticastEntry 5 }

    hwXQoSQueueStatisticsMulticastPassBytesRate OBJECT-TYPE
        SYNTAX Counter64
        MAX-ACCESS read-only
        STATUS current
        DESCRIPTION
            "The passed Bytes rate of the queue."
        ::= { hwXQoSQueueStatisticsMulticastEntry 6 }

    hwXQoSQueueStatisticsMulticastDropPkts OBJECT-TYPE
        SYNTAX Counter64
        MAX-ACCESS read-only
        STATUS current
        DESCRIPTION
            "The dropped packets count of the queue."
        ::= { hwXQoSQueueStatisticsMulticastEntry 7 }

    hwXQoSQueueStatisticsMulticastDropBytes OBJECT-TYPE
        SYNTAX Counter64
        MAX-ACCESS read-only
        STATUS current
        DESCRIPTION
            "The dropped Bytes count of the queue."
        ::= { hwXQoSQueueStatisticsMulticastEntry 8 }

    hwXQoSQueueStatisticsMulticastDropPktsRate OBJECT-TYPE
        SYNTAX Counter64
        MAX-ACCESS read-only
        STATUS current
        DESCRIPTION
            "The dropped packets rate of the queue."
        ::= { hwXQoSQueueStatisticsMulticastEntry 9 }

    hwXQoSQueueStatisticsMulticastDropBytesRate OBJECT-TYPE
        SYNTAX Counter64
        MAX-ACCESS read-only
        STATUS current
        DESCRIPTION
            "The dropped Bytes rate of the queue."
        ::= { hwXQoSQueueStatisticsMulticastEntry 10 }


    hwXQoSInterfaceIngressDropAlarmObjects OBJECT IDENTIFIER ::= { hwXQoSObjects 57 }

    hwXQoSInterfaceIngressDropAlarmTable OBJECT-TYPE
        SYNTAX SEQUENCE OF HwXQoSInterfaceIngressDropAlarmEntry
        MAX-ACCESS not-accessible
        STATUS current
        DESCRIPTION
            "hwXQoSInterfaceIngressDropAlarmTable"
        ::= { hwXQoSInterfaceIngressDropAlarmObjects 1 }

    hwXQoSInterfaceIngressDropAlarmEntry OBJECT-TYPE
        SYNTAX HwXQoSInterfaceIngressDropAlarmEntry
        MAX-ACCESS not-accessible
        STATUS current
        DESCRIPTION
            "hwXQoSInterfaceIngressDropAlarmEntry"
        INDEX { hwXQoSInterfaceIngressDropAlarmIfName }
        ::= { hwXQoSInterfaceIngressDropAlarmTable 1 }

    HwXQoSInterfaceIngressDropAlarmEntry ::=
        SEQUENCE {
            hwXQoSInterfaceIngressDropAlarmIfName
                OCTET STRING
                }

    hwXQoSInterfaceIngressDropAlarmIfName OBJECT-TYPE
        SYNTAX OCTET STRING
        MAX-ACCESS read-only
        STATUS current
        DESCRIPTION
            "interface name."
        ::= { hwXQoSInterfaceIngressDropAlarmEntry 1 }

    hwXACLEPGGroupMemberAlarmObjects OBJECT IDENTIFIER ::= { hwXQoSObjects 59 }

    hwXACLEPGGroupMemberAlarmTable OBJECT-TYPE
        SYNTAX SEQUENCE OF HwXACLEPGGroupMemberAlarmEntry
        MAX-ACCESS not-accessible
        STATUS current
        DESCRIPTION
            "hwXACLEPGGroupMemberAlarmTable"
        ::= { hwXACLEPGGroupMemberAlarmObjects 1 }

    hwXACLEPGGroupMemberAlarmEntry OBJECT-TYPE
        SYNTAX HwXACLEPGGroupMemberAlarmEntry
        MAX-ACCESS not-accessible
        STATUS current
        DESCRIPTION
            "hwXACLEPGGroupMemberAlarmEntry"
        INDEX { hwXAclEpgGroupMemberAlarmIPAddress, hwXAclEpgGroupMemberAlarmIPMask, hwXAclEpgGroupMemberAlarmVpnInstanceName, hwXAclEpgGroupMemberAlarmSegmentId, hwXAclEpgGroupMemberAlarmSlotid}
        ::= { hwXACLEPGGroupMemberAlarmTable 1 }

    HwXACLEPGGroupMemberAlarmEntry ::=
        SEQUENCE {
        hwXAclEpgGroupMemberAlarmIPAddress
                IpAddress,
        hwXAclEpgGroupMemberAlarmIPMask
                IpAddress,
        hwXAclEpgGroupMemberAlarmVpnInstanceName
                OCTET STRING,
        hwXAclEpgGroupMemberAlarmSegmentId
                OCTET STRING,
        hwXAclEpgGroupMemberAlarmSlotid
                OCTET STRING
                }

    hwXAclEpgGroupMemberAlarmIPAddress OBJECT-TYPE
        SYNTAX IpAddress
        MAX-ACCESS read-only
        STATUS current
        DESCRIPTION
            "segment member ip-address."
        ::= { hwXACLEPGGroupMemberAlarmEntry 1 }
    hwXAclEpgGroupMemberAlarmIPMask OBJECT-TYPE
        SYNTAX IpAddress
        MAX-ACCESS read-only
        STATUS current
        DESCRIPTION
            "segment member ip-address mask."
        ::= { hwXACLEPGGroupMemberAlarmEntry 2 }
    hwXAclEpgGroupMemberAlarmVpnInstanceName OBJECT-TYPE
        SYNTAX OCTET STRING
        MAX-ACCESS read-only
        STATUS current
        DESCRIPTION
            "vpn-instance."
        ::= { hwXACLEPGGroupMemberAlarmEntry 3 }
    hwXAclEpgGroupMemberAlarmSegmentId OBJECT-TYPE
        SYNTAX OCTET STRING
        MAX-ACCESS read-only
        STATUS current
        DESCRIPTION
            "segment id."
        ::= { hwXACLEPGGroupMemberAlarmEntry 4 }
    hwXAclEpgGroupMemberAlarmSlotid OBJECT-TYPE
        SYNTAX OCTET STRING
        MAX-ACCESS read-only
        STATUS current
        DESCRIPTION
            "slot id."
        ::= { hwXACLEPGGroupMemberAlarmEntry 5 }

    hwXACLEPGGroupMemberV6AlarmTable OBJECT-TYPE
        SYNTAX SEQUENCE OF HwXACLEPGGroupMemberV6AlarmEntry
        MAX-ACCESS not-accessible
        STATUS current
        DESCRIPTION
            "hwXACLEPGGroupMemberV6AlarmTable"
        ::= { hwXACLEPGGroupMemberAlarmObjects 2 }

    hwXACLEPGGroupMemberV6AlarmEntry OBJECT-TYPE
        SYNTAX HwXACLEPGGroupMemberV6AlarmEntry
        MAX-ACCESS not-accessible
        STATUS current
        DESCRIPTION
            "hwXACLEPGGroupMemberV6AlarmEntry"
        INDEX { hwXAclEpgGroupMemberV6AlarmIPv6Address, hwXAclEpgGroupMemberV6AlarmIPv6Mask, hwXAclEpgGroupMemberV6AlarmVpnInstanceName, hwXAclEpgGroupMemberV6AlarmSegmentId, hwXAclEpgGroupMemberV6AlarmSlotid}
        ::= { hwXACLEPGGroupMemberV6AlarmTable 1 }

    HwXACLEPGGroupMemberV6AlarmEntry ::=
        SEQUENCE {
        hwXAclEpgGroupMemberV6AlarmIPv6Address
                OCTET STRING,
        hwXAclEpgGroupMemberV6AlarmIPv6Mask
                OCTET STRING,
        hwXAclEpgGroupMemberV6AlarmVpnInstanceName
                OCTET STRING,
        hwXAclEpgGroupMemberV6AlarmSegmentId
                OCTET STRING,
        hwXAclEpgGroupMemberV6AlarmSlotid
                OCTET STRING
                }

    hwXAclEpgGroupMemberV6AlarmIPv6Address OBJECT-TYPE
        SYNTAX OCTET STRING
        MAX-ACCESS read-only
        STATUS current
        DESCRIPTION
            "segment member ipv6-address."
        ::= { hwXACLEPGGroupMemberV6AlarmEntry 1 }
    hwXAclEpgGroupMemberV6AlarmIPv6Mask OBJECT-TYPE
        SYNTAX OCTET STRING
        MAX-ACCESS read-only
        STATUS current
        DESCRIPTION
            "segment member ipv6-address mask."
        ::= { hwXACLEPGGroupMemberV6AlarmEntry 2 }
    hwXAclEpgGroupMemberV6AlarmVpnInstanceName OBJECT-TYPE
        SYNTAX OCTET STRING
        MAX-ACCESS read-only
        STATUS current
        DESCRIPTION
            "vpn-instance."
        ::= { hwXACLEPGGroupMemberV6AlarmEntry 3 }
    hwXAclEpgGroupMemberV6AlarmSegmentId OBJECT-TYPE
        SYNTAX OCTET STRING
        MAX-ACCESS read-only
        STATUS current
        DESCRIPTION
            "segment id."
        ::= { hwXACLEPGGroupMemberV6AlarmEntry 4 }
    hwXAclEpgGroupMemberV6AlarmSlotid OBJECT-TYPE
        SYNTAX OCTET STRING
        MAX-ACCESS read-only
        STATUS current
        DESCRIPTION
            "slot id."
        ::= { hwXACLEPGGroupMemberV6AlarmEntry 5 }

    hwXACLEPGPolicyAlarmObjects OBJECT IDENTIFIER ::= { hwXQoSObjects 60 }

    hwXACLEPGPolicyAlarmTable OBJECT-TYPE
        SYNTAX SEQUENCE OF HwXACLEPGPolicyAlarmEntry
        MAX-ACCESS not-accessible
        STATUS current
        DESCRIPTION
            "hwXACLEPGPolicyAlarmTable"
        ::= { hwXACLEPGPolicyAlarmObjects 1 }

    hwXACLEPGPolicyAlarmEntry OBJECT-TYPE
        SYNTAX HwXACLEPGPolicyAlarmEntry
        MAX-ACCESS not-accessible
        STATUS current
        DESCRIPTION
            "hwXACLEPGPolicyAlarmEntry"
        INDEX { hwXAclEpgPolicyAlarmSourceSegmentId, hwXAclEpgPolicyAlarmDestinationSegmentId, hwXAclEpgPolicyAlarmProtocol, hwXAclEpgPolicyAlarmSourceport, hwXAclEpgPolicyAlarmDestinationport, hwXAclEpgPolicyAlarmClassifier, hwXAclEpgPolicyAlarmSlotid}
        ::= { hwXACLEPGPolicyAlarmTable 1 }

    HwXACLEPGPolicyAlarmEntry ::=
        SEQUENCE {
        hwXAclEpgPolicyAlarmSourceSegmentId
                OCTET STRING,
        hwXAclEpgPolicyAlarmDestinationSegmentId
                OCTET STRING,
        hwXAclEpgPolicyAlarmProtocol
                OCTET STRING,
        hwXAclEpgPolicyAlarmSourceport
                OCTET STRING,
        hwXAclEpgPolicyAlarmDestinationport
                OCTET STRING,
        hwXAclEpgPolicyAlarmClassifier
                OCTET STRING,
        hwXAclEpgPolicyAlarmSlotid
                OCTET STRING
                }

    hwXAclEpgPolicyAlarmSourceSegmentId OBJECT-TYPE
        SYNTAX OCTET STRING
        MAX-ACCESS read-only
        STATUS current
        DESCRIPTION
            "source segment id."
        ::= { hwXACLEPGPolicyAlarmEntry 1 }
    hwXAclEpgPolicyAlarmDestinationSegmentId OBJECT-TYPE
        SYNTAX OCTET STRING
        MAX-ACCESS read-only
        STATUS current
        DESCRIPTION
            "destination segment id."
        ::= { hwXACLEPGPolicyAlarmEntry 2 }
    hwXAclEpgPolicyAlarmProtocol OBJECT-TYPE
        SYNTAX OCTET STRING
        MAX-ACCESS read-only
        STATUS current
        DESCRIPTION
            "protocol."
        ::= { hwXACLEPGPolicyAlarmEntry 3 }
    hwXAclEpgPolicyAlarmSourceport OBJECT-TYPE
        SYNTAX OCTET STRING
        MAX-ACCESS read-only
        STATUS current
        DESCRIPTION
            "source-port."
        ::= { hwXACLEPGPolicyAlarmEntry 4 }
    hwXAclEpgPolicyAlarmDestinationport OBJECT-TYPE
        SYNTAX OCTET STRING
        MAX-ACCESS read-only
        STATUS current
        DESCRIPTION
            "destination-port."
        ::= { hwXACLEPGPolicyAlarmEntry 5 }
    hwXAclEpgPolicyAlarmClassifier OBJECT-TYPE
        SYNTAX OCTET STRING
        MAX-ACCESS read-only
        STATUS current
        DESCRIPTION
            "classifier."
        ::= { hwXACLEPGPolicyAlarmEntry 6 }
    hwXAclEpgPolicyAlarmSlotid OBJECT-TYPE
        SYNTAX OCTET STRING
        MAX-ACCESS read-only
        STATUS current
        DESCRIPTION
            "slot id."
        ::= { hwXACLEPGPolicyAlarmEntry 7 }

    hwXACLEPGCreateGroupAlarmObjects OBJECT IDENTIFIER ::= { hwXQoSObjects 61 }

    hwXACLEPGCreateGroupAlarmTable OBJECT-TYPE
        SYNTAX SEQUENCE OF HwXACLEPGCreateGroupAlarmEntry
        MAX-ACCESS not-accessible
        STATUS current
        DESCRIPTION
            "hwXACLEPGCreateGroupAlarmTable"
        ::= { hwXACLEPGCreateGroupAlarmObjects 1 }

    hwXACLEPGCreateGroupAlarmEntry OBJECT-TYPE
        SYNTAX HwXACLEPGCreateGroupAlarmEntry
        MAX-ACCESS not-accessible
        STATUS current
        DESCRIPTION
            "hwXACLEPGCreateGroupAlarmEntry"
        INDEX { hwXACLEPGCreateGroupAlarmSlotid, hwXACLEPGCreateGroupAlarmSegmentid}
        ::= { hwXACLEPGCreateGroupAlarmTable 1 }

    HwXACLEPGCreateGroupAlarmEntry ::=
        SEQUENCE {
            hwXACLEPGCreateGroupAlarmSlotid
                OCTET STRING,
            hwXACLEPGCreateGroupAlarmSegmentid
                Integer32
                }

    hwXACLEPGCreateGroupAlarmSlotid OBJECT-TYPE
        SYNTAX OCTET STRING
        MAX-ACCESS read-only
        STATUS current
        DESCRIPTION
            "slot id."
        ::= { hwXACLEPGCreateGroupAlarmEntry 1 }
    hwXACLEPGCreateGroupAlarmSegmentid OBJECT-TYPE
        SYNTAX Integer32
        MAX-ACCESS read-only
        STATUS current
        DESCRIPTION
            "segment id."
        ::= { hwXACLEPGCreateGroupAlarmEntry 2 }

    hwXQoSPfcApplyFailAlarmObjects OBJECT IDENTIFIER ::= { hwXQoSObjects 62 }

    hwXQoSPfcApplyFailAlarmTable OBJECT-TYPE
        SYNTAX SEQUENCE OF HwXQoSPfcApplyFailAlarmEntry
        MAX-ACCESS not-accessible
        STATUS current
        DESCRIPTION
            "hwXQoSPfcApplyFailAlarmTable"
        ::= { hwXQoSPfcApplyFailAlarmObjects 1 }

    hwXQoSPfcApplyFailAlarmEntry OBJECT-TYPE
        SYNTAX HwXQoSPfcApplyFailAlarmEntry
        MAX-ACCESS not-accessible
        STATUS current
        DESCRIPTION
            "hwXQoSPfcApplyFailAlarmEntry"
        INDEX { hwXQoSPfcApplyFailAlarmIfName }
        ::= { hwXQoSPfcApplyFailAlarmTable 1 }

    HwXQoSPfcApplyFailAlarmEntry ::=
        SEQUENCE {
            hwXQoSPfcApplyFailAlarmIfName
                OCTET STRING
                }

    hwXQoSPfcApplyFailAlarmIfName OBJECT-TYPE
        SYNTAX OCTET STRING
        MAX-ACCESS accessible-for-notify
        STATUS current
        DESCRIPTION
            "ifname."
        ::= { hwXQoSPfcApplyFailAlarmEntry 1 }

    hwXQoSPfcApplyFailAlarmResumeObjects OBJECT IDENTIFIER ::= { hwXQoSObjects 63 }

    hwXQoSPfcApplyFailAlarmResumeTable OBJECT-TYPE
        SYNTAX SEQUENCE OF HwXQoSPfcApplyFailAlarmResumeEntry
        MAX-ACCESS not-accessible
        STATUS current
        DESCRIPTION
            "hwXQoSPfcApplyFailAlarmResumeTable"
        ::= { hwXQoSPfcApplyFailAlarmResumeObjects 1 }

    hwXQoSPfcApplyFailAlarmResumeEntry OBJECT-TYPE
        SYNTAX HwXQoSPfcApplyFailAlarmResumeEntry
        MAX-ACCESS not-accessible
        STATUS current
        DESCRIPTION
            "hwXQoSPfcApplyFailAlarmResumeEntry"
        INDEX { hwXQoSPfcApplyFailAlarmResumeIfName }
        ::= { hwXQoSPfcApplyFailAlarmResumeTable 1 }

    HwXQoSPfcApplyFailAlarmResumeEntry ::=
        SEQUENCE {
            hwXQoSPfcApplyFailAlarmResumeIfName
                OCTET STRING
                }

    hwXQoSPfcApplyFailAlarmResumeIfName OBJECT-TYPE
        SYNTAX OCTET STRING
        MAX-ACCESS accessible-for-notify
        STATUS current
        DESCRIPTION
            "ifname."
        ::= { hwXQoSPfcApplyFailAlarmResumeEntry 1 }


    hwXACLEPGEnableAlarmObjects OBJECT IDENTIFIER ::= { hwXQoSObjects 64 }

    hwXACLEPGEnableAlarmTable OBJECT-TYPE
        SYNTAX SEQUENCE OF HwXACLEPGEnableAlarmEntry
        MAX-ACCESS not-accessible
        STATUS current
        DESCRIPTION
            "hwXACLEPGEnableAlarmTable"
        ::= { hwXACLEPGEnableAlarmObjects 1 }

    hwXACLEPGEnableAlarmEntry OBJECT-TYPE
        SYNTAX HwXACLEPGEnableAlarmEntry
        MAX-ACCESS not-accessible
        STATUS current
        DESCRIPTION
            "hwXACLEPGEnableAlarmEntry"
        INDEX { hwXACLEPGEnableAlarmSlotid}
        ::= { hwXACLEPGEnableAlarmTable 1 }

    HwXACLEPGEnableAlarmEntry ::=
        SEQUENCE {
            hwXACLEPGEnableAlarmSlotid
                OCTET STRING
                }

    hwXACLEPGEnableAlarmSlotid OBJECT-TYPE
        SYNTAX OCTET STRING
        MAX-ACCESS read-only
        STATUS current
        DESCRIPTION
            "slot id."
        ::= { hwXACLEPGEnableAlarmEntry 1 }

    hwXQOSFlowControlAlarm  NOTIFICATION-TYPE
        OBJECTS {
	        hwXQOSFlowControlAlarmSlotid,
            hwXQOSFlowControlAlarmIfIndex,
	        hwXQOSFlowControlAlarmIfName
	}
        STATUS current
        DESCRIPTION
	        "The SNMP trap is generated when abnormal pause frame received."
        ::= { hwXQoSNotifications 95}

   hwXQOSFlowControlAlarmResume NOTIFICATION-TYPE
        OBJECTS {
	        hwXQOSFlowControlAlarmSlotid,
            hwXQOSFlowControlAlarmIfIndex,
	        hwXQOSFlowControlAlarmIfName
	}
        STATUS current
        DESCRIPTION
	        "Clear the SNMP trap which is generated when abnormal pause frame received."
        ::= { hwXQoSNotifications 96}

--begin add by yangting
    hwXQoSRedirectNextHopLackResAlarm NOTIFICATION-TYPE
        OBJECTS {
            hwXQoSRedirectNextHopLackResAlarmBehaviorName,
            hwXQoSRedirectNextHopLackResAlarmSlotID,
            hwXQoSRedirectNextHopLackResAlarmRdrType }
        STATUS current
        DESCRIPTION
            "The SNMP trap is generated when the redirecting traffic to the next hop is invalid due to insufficient NHP resources."
        ::= { hwXQoSNotifications 111 }

    hwXQoSRedirectNextHopLackResAlarmClear NOTIFICATION-TYPE
        OBJECTS {
            hwXQoSRedirectNextHopLackResAlarmBehaviorName,
            hwXQoSRedirectNextHopLackResAlarmSlotID,
            hwXQoSRedirectNextHopLackResAlarmRdrType }
        STATUS current
        DESCRIPTION
            "Clear the SNMP trap is generated when resources are sufficient or the configuration of redirecting traffic to the next hop is deleted."
        ::= { hwXQoSNotifications 112 }
--end add by yangting

--begin
	hwXQoSPfcRxRateAlarm NOTIFICATION-TYPE
		OBJECTS { 
			hwXQoSPfcRxRateAlarmIfName,
			hwXQoSPfcRxRateAlarmPriority,
			hwXQoSPfcRxRateAlarmReceivedrate,
			hwXQoSPfcRxRateAlarmThreshold
			}
		STATUS current
		DESCRIPTION 
			"The SNMP trap is generated when the rate of received PFC frames exceeds the threshold."
		::= { hwXQoSNotifications 165}
	
	hwXQoSPfcRxRateResume NOTIFICATION-TYPE
		OBJECTS { 
			hwXQoSPfcRxRateAlarmIfName,
			hwXQoSPfcRxRateAlarmPriority
			}
		STATUS current
		DESCRIPTION 
			"Clear the SNMP trap which is generated when the rate of received PFC frames falls below the threshold or the alarm configuration is deleted."
		::= { hwXQoSNotifications 166}

	hwXQoSPfcTxRateAlarm NOTIFICATION-TYPE
		OBJECTS { 
			hwXQoSPfcTxRateAlarmIfName,
			hwXQoSPfcTxRateAlarmPriority,
			hwXQoSPfcTxRateAlarmTransmittedrate,
			hwXQoSPfcTxRateAlarmThreshold
			}
		STATUS current
		DESCRIPTION 
			"The SNMP trap is generated when the rate of transmitted PFC frames exceeds the threshold."
		::= { hwXQoSNotifications 167}
	
	hwXQoSPfcTxRateResume NOTIFICATION-TYPE
		OBJECTS { 
			hwXQoSPfcTxRateAlarmIfName,
			hwXQoSPfcTxRateAlarmPriority
			}
		STATUS current
		DESCRIPTION 
			"Clear the SNMP trap which is generated when the rate of transmitted PFC frames falls below the threshold or the alarm configuration is deleted."
		::= { hwXQoSNotifications 168}
--end

--begin add by wangzhiqiang
    hwXQosHeadRoomPoolApplyFailAlarm NOTIFICATION-TYPE
        OBJECTS { 
            hwXQosHeadRoomPoolApplyFailAlarmSlotId
            }
        STATUS current
        DESCRIPTION 
            "The SNMP trap is generated when headroom-pool configure failed."
        ::= { hwXQoSNotifications 169}
    hwXQosHeadRoomPoolApplyFailAlarmResume NOTIFICATION-TYPE
        OBJECTS { 
            hwXQosHeadRoomPoolApplyFailAlarmSlotId
            }
        STATUS current
        DESCRIPTION 
            "The SNMP trap is generated when headroom-pool configure succeed."
        ::= { hwXQoSNotifications 170}
    hwXQosPfcBufferApplyFailAlarm NOTIFICATION-TYPE
        OBJECTS { 
            hwXQosPfcBufferApplyFailAlarmIfName,
	    hwXQosPfcBufferApplyFailAlarmPriority,
            hwXQosPfcBufferApplyFailAlarmBufferType
            }
        STATUS current
        DESCRIPTION 
            "The SNMP trap is generated when PFC buffer configure failed."
        ::= { hwXQoSNotifications 171}
    hwXQosPfcBufferApplyFailAlarmResume NOTIFICATION-TYPE
        OBJECTS { 
            hwXQosPfcBufferApplyFailAlarmIfName,
	    hwXQosPfcBufferApplyFailAlarmPriority,
            hwXQosPfcBufferApplyFailAlarmBufferType
            }
        STATUS current
        DESCRIPTION 
            "The SNMP trap is generated when PFC buffer configure succeed."
        ::= { hwXQoSNotifications 172}
--end

    hwXQOSFlowControlAlarmObjects OBJECT IDENTIFIER ::= { hwXQoSObjects 65 }

    hwXQOSFlowControlAlarmTable OBJECT-TYPE
        SYNTAX SEQUENCE OF HwXQOSFlowControlAlarmEntry
        MAX-ACCESS not-accessible
        STATUS current
        DESCRIPTION
            "hwXQOSFlowControlAlarmTable"
        ::= { hwXQOSFlowControlAlarmObjects 1 }

    hwXQOSFlowControlAlarmEntry OBJECT-TYPE
        SYNTAX HwXQOSFlowControlAlarmEntry
        MAX-ACCESS not-accessible
        STATUS current
        DESCRIPTION
            "hwXQOSFlowControlAlarmEntry"
        INDEX {hwXQOSFlowControlAlarmSlotid, hwXQOSFlowControlAlarmIfIndex, hwXQOSFlowControlAlarmIfName}
        ::= { hwXQOSFlowControlAlarmTable 1 }

    HwXQOSFlowControlAlarmEntry ::=
        SEQUENCE {
            hwXQOSFlowControlAlarmSlotid
                OCTET STRING,
            hwXQOSFlowControlAlarmIfIndex
                Integer32,
            hwXQOSFlowControlAlarmIfName
                OCTET STRING
                }

    hwXQOSFlowControlAlarmSlotid OBJECT-TYPE
        SYNTAX OCTET STRING
        MAX-ACCESS read-only
        STATUS current
        DESCRIPTION
            "slot id."
        ::= { hwXQOSFlowControlAlarmEntry 1 }

    hwXQOSFlowControlAlarmIfIndex OBJECT-TYPE
        SYNTAX Integer32
        MAX-ACCESS read-only
        STATUS current
        DESCRIPTION
            "ifindex."
        ::= { hwXQOSFlowControlAlarmEntry 2 }

    hwXQOSFlowControlAlarmIfName OBJECT-TYPE
        SYNTAX OCTET STRING
        MAX-ACCESS read-only
        STATUS current
        DESCRIPTION
            "interface name."
        ::= { hwXQOSFlowControlAlarmEntry 3 }


    hwXACLResourceAlarmObjects OBJECT IDENTIFIER ::= { hwXQoSObjects 66 }

    hwXACLResourceAlarmTable OBJECT-TYPE
        SYNTAX SEQUENCE OF HwXACLResourceAlarmEntry
        MAX-ACCESS not-accessible
        STATUS current
        DESCRIPTION
            "hwXACLResourceAlarmTable"
        ::= { hwXACLResourceAlarmObjects 1 }

    hwXACLResourceAlarmEntry OBJECT-TYPE
        SYNTAX HwXACLResourceAlarmEntry
        MAX-ACCESS not-accessible
        STATUS current
        DESCRIPTION
            "hwXACLResourceAlarmEntry"
        INDEX {hwXACLResourceAlarmSlotid, hwXACLResourceAlarmServiceType, hwXACLResourceAlarmServiceName, hwXACLResourceAlarmApplyType, hwXACLResourceAlarmInterfaceName, hwXACLResourceAlarmDirection, hwXACLResourceAlarmServiceParam1, hwXACLResourceAlarmServiceParam2, hwXACLResourceAlarmServiceParam3, hwXACLResourceAlarmACLFailReason}
        ::= { hwXACLResourceAlarmTable 1 }

    HwXACLResourceAlarmEntry ::=
        SEQUENCE {
            hwXACLResourceAlarmSlotid
                OCTET STRING,
            hwXACLResourceAlarmServiceType
                OCTET STRING,
            hwXACLResourceAlarmServiceName
                OCTET STRING,
            hwXACLResourceAlarmApplyType
                OCTET STRING,
            hwXACLResourceAlarmInterfaceName
                OCTET STRING,
            hwXACLResourceAlarmDirection
                OCTET STRING,
            hwXACLResourceAlarmServiceParam1
                OCTET STRING,
            hwXACLResourceAlarmServiceParam2
                OCTET STRING,
            hwXACLResourceAlarmServiceParam3
                OCTET STRING,
            hwXACLResourceAlarmACLFailReason
                OCTET STRING
                }
    hwXACLResourceAlarmSlotid OBJECT-TYPE
        SYNTAX OCTET STRING
        MAX-ACCESS read-only
        STATUS current
        DESCRIPTION
            "The information of the chassis."
        ::= { hwXACLResourceAlarmEntry 1 }

    hwXACLResourceAlarmServiceType OBJECT-TYPE
        SYNTAX OCTET STRING
        MAX-ACCESS read-only
        STATUS current
        DESCRIPTION
            "Service Type."
        ::= { hwXACLResourceAlarmEntry 2 }
    hwXACLResourceAlarmServiceName OBJECT-TYPE
        SYNTAX OCTET STRING
        MAX-ACCESS read-only
        STATUS current
        DESCRIPTION
            "Service Name."
        ::= { hwXACLResourceAlarmEntry 3 }
    hwXACLResourceAlarmApplyType OBJECT-TYPE
        SYNTAX OCTET STRING
        MAX-ACCESS read-only
        STATUS current
        DESCRIPTION
            "View."
        ::= { hwXACLResourceAlarmEntry 4 }
    hwXACLResourceAlarmInterfaceName OBJECT-TYPE
        SYNTAX OCTET STRING
        MAX-ACCESS read-only
        STATUS current
        DESCRIPTION
            "Interface Name."
        ::= { hwXACLResourceAlarmEntry 5 }
    hwXACLResourceAlarmDirection OBJECT-TYPE
        SYNTAX OCTET STRING
        MAX-ACCESS read-only
        STATUS current
        DESCRIPTION
            "inbound or outbound."
        ::= { hwXACLResourceAlarmEntry 6 }
    hwXACLResourceAlarmServiceParam1 OBJECT-TYPE
        SYNTAX OCTET STRING
        MAX-ACCESS read-only
        STATUS current
        DESCRIPTION
            "Service Param1."
        ::= { hwXACLResourceAlarmEntry 7 }
    hwXACLResourceAlarmServiceParam2 OBJECT-TYPE
        SYNTAX OCTET STRING
        MAX-ACCESS read-only
        STATUS current
        DESCRIPTION
            "Service Param2."
        ::= { hwXACLResourceAlarmEntry 8 }
    hwXACLResourceAlarmServiceParam3 OBJECT-TYPE
        SYNTAX OCTET STRING
        MAX-ACCESS read-only
        STATUS current
        DESCRIPTION
            "Service Param3."
        ::= { hwXACLResourceAlarmEntry 9 }

    hwXACLResourceAlarmACLFailReason OBJECT-TYPE
        SYNTAX OCTET STRING
        MAX-ACCESS read-only
        STATUS current
        DESCRIPTION
            "Acl Fail Code."
        ::= { hwXACLResourceAlarmEntry 10 }

    hwEnpPerformanceAlarmObjects OBJECT IDENTIFIER ::= { hwXQoSObjects 67 }

    hwEnpPerformanceAlarmTable OBJECT-TYPE
        SYNTAX SEQUENCE OF HwEnpPerformanceAlarmEntry
        MAX-ACCESS not-accessible
        STATUS current
        DESCRIPTION
            "hwEnpPerformanceAlarmTable"
        ::= { hwEnpPerformanceAlarmObjects 1 }

    hwEnpPerformanceAlarmEntry OBJECT-TYPE
        SYNTAX HwEnpPerformanceAlarmEntry
        MAX-ACCESS not-accessible
        STATUS current
        DESCRIPTION
            "hwEnpPerformanceAlarmEntry"
        INDEX {hwEnpPerformanceAlarmSlotid}
        ::= { hwEnpPerformanceAlarmTable 1 }

    HwEnpPerformanceAlarmEntry ::=
        SEQUENCE {
            hwEnpPerformanceAlarmSlotid
                OCTET STRING
                }

    hwEnpPerformanceAlarmSlotid OBJECT-TYPE
        SYNTAX OCTET STRING
        MAX-ACCESS read-only
        STATUS current
        DESCRIPTION
            "The information of the chassis."
        ::= { hwEnpPerformanceAlarmEntry 1 }

    hwXQoSResourceAlarmObjects OBJECT IDENTIFIER ::= { hwXQoSObjects 107 }

    hwXQoSResourceAlarmTable OBJECT-TYPE
        SYNTAX SEQUENCE OF HwXQoSResourceAlarmEntry
        MAX-ACCESS not-accessible
        STATUS current
        DESCRIPTION
            "hwXQoSResourceAlarmTable"
        ::= { hwXQoSResourceAlarmObjects 1 }

    hwXQoSResourceAlarmEntry OBJECT-TYPE
        SYNTAX HwXQoSResourceAlarmEntry
        MAX-ACCESS not-accessible
        STATUS current
        DESCRIPTION
            "hwXQoSResourceAlarmEntry"
        INDEX { hwXQoSResourceAlarmSlotID, hwXQoSResourceAlarmType, hwXQoSResourceAlarmServiceType }
        ::= { hwXQoSResourceAlarmTable 1 }

    HwXQoSResourceAlarmEntry ::=
        SEQUENCE {
            hwXQoSResourceAlarmSlotID
                Integer32,
            hwXQoSResourceAlarmType
                OCTET STRING,
            hwXQoSResourceAlarmServiceType
                OCTET STRING
                }

    hwXQoSResourceAlarmSlotID OBJECT-TYPE
        SYNTAX Integer32
        MAX-ACCESS read-only
        STATUS current
        DESCRIPTION
            "Slot ID."
        ::= { hwXQoSResourceAlarmEntry 1 }

    hwXQoSResourceAlarmType OBJECT-TYPE
        SYNTAX OCTET STRING
        MAX-ACCESS read-only
        STATUS current
        DESCRIPTION
            "Resource type."
        ::= { hwXQoSResourceAlarmEntry 2 }
    hwXQoSResourceAlarmServiceType OBJECT-TYPE
        SYNTAX OCTET STRING
        MAX-ACCESS read-only
        STATUS current
        DESCRIPTION
            "Service type."
        ::= { hwXQoSResourceAlarmEntry 3 }


    hwXQoSResourceOverrunAlarmObjects OBJECT IDENTIFIER ::= { hwXQoSObjects 108 }

    hwXQoSResourceOverrunAlarmTable OBJECT-TYPE
        SYNTAX SEQUENCE OF HwXQoSResourceOverrunAlarmEntry
        MAX-ACCESS not-accessible
        STATUS current
        DESCRIPTION
            "hwXQoSResourceOverrunAlarmTable"
        ::= { hwXQoSResourceOverrunAlarmObjects 1 }

    hwXQoSResourceOverrunAlarmEntry OBJECT-TYPE
        SYNTAX HwXQoSResourceOverrunAlarmEntry
        MAX-ACCESS not-accessible
        STATUS current
        DESCRIPTION
            "hwXQoSResourceOverrunAlarmEntry"
        INDEX { hwXQoSResourceOverrunAlarmSlotID, hwXQoSResourceOverrunAlarmType, hwXQoSResourceOverrunAlarmTotal, hwXQoSResourceOverrunAlarmFree, hwXQoSResourceOverrunAlarmThreshold }
        ::= { hwXQoSResourceOverrunAlarmTable 1 }

    HwXQoSResourceOverrunAlarmEntry ::=
        SEQUENCE {
            hwXQoSResourceOverrunAlarmSlotID
                Integer32,
            hwXQoSResourceOverrunAlarmType
                OCTET STRING,
			hwXQoSResourceOverrunAlarmTotal
                Integer32,
			hwXQoSResourceOverrunAlarmFree
                Integer32,
			hwXQoSResourceOverrunAlarmThreshold
                Integer32
                }

    hwXQoSResourceOverrunAlarmSlotID OBJECT-TYPE
        SYNTAX Integer32
        MAX-ACCESS read-only
        STATUS current
        DESCRIPTION
            "Slot ID."
        ::= { hwXQoSResourceOverrunAlarmEntry 1 }

    hwXQoSResourceOverrunAlarmType OBJECT-TYPE
        SYNTAX OCTET STRING
        MAX-ACCESS read-only
        STATUS current
        DESCRIPTION
            "Resource type."
        ::= { hwXQoSResourceOverrunAlarmEntry 2 }
    hwXQoSResourceOverrunAlarmTotal OBJECT-TYPE
        SYNTAX Integer32
        MAX-ACCESS read-only
        STATUS current
        DESCRIPTION
            "Total number of resources."
        ::= { hwXQoSResourceOverrunAlarmEntry 3 }

    hwXQoSResourceOverrunAlarmFree OBJECT-TYPE
        SYNTAX Integer32
        MAX-ACCESS read-only
        STATUS current
        DESCRIPTION
            "Number of remaining resources."
        ::= { hwXQoSResourceOverrunAlarmEntry 4 }

    hwXQoSResourceOverrunAlarmThreshold OBJECT-TYPE
        SYNTAX Integer32
        MAX-ACCESS read-only
        STATUS current
        DESCRIPTION
            "Resource usage alarm threshold."
        ::= { hwXQoSResourceOverrunAlarmEntry 5 }


--begin add by guanqingyu
    hwXQoSUnsupportedFeatureAlarmObjects OBJECT IDENTIFIER ::= { hwXQoSObjects 109 }

    hwXQoSUnsupportedFeatureAlarmTable OBJECT-TYPE
        SYNTAX SEQUENCE OF HwXQoSUnsupportedFeatureAlarmEntry
        MAX-ACCESS not-accessible
        STATUS current
        DESCRIPTION
            "hwXQoSUnsupportedFeatureAlarmTable"
        ::= { hwXQoSUnsupportedFeatureAlarmObjects 1 }

    hwXQoSUnsupportedFeatureAlarmEntry OBJECT-TYPE
        SYNTAX HwXQoSUnsupportedFeatureAlarmEntry
        MAX-ACCESS not-accessible
        STATUS current
        DESCRIPTION
            "hwXQoSUnsupportedFeatureAlarmEntry"
        INDEX { hwXQoSUnsupportedFeatureAlarmBoardID, hwXQoSUnsupportedFeatureAlarmFeatureType }
        ::= { hwXQoSUnsupportedFeatureAlarmTable 1 }

    HwXQoSUnsupportedFeatureAlarmEntry ::=
        SEQUENCE {
            hwXQoSUnsupportedFeatureAlarmBoardID
                OCTET STRING,
            hwXQoSUnsupportedFeatureAlarmFeatureType
                INTEGER
                }

    hwXQoSUnsupportedFeatureAlarmBoardID OBJECT-TYPE
        SYNTAX OCTET STRING
        MAX-ACCESS read-only
        STATUS current
        DESCRIPTION
            "Board ID."
        ::= { hwXQoSUnsupportedFeatureAlarmEntry 1 }

    hwXQoSUnsupportedFeatureAlarmFeatureType OBJECT-TYPE
        SYNTAX INTEGER
            {
                bgpflow(1),
                qppb(2),
                behaviorofnetstream(3),
                behaviorofstrictipurpf(4),
                bgpflowvxlanpop(5)
            }
        MAX-ACCESS read-only
        STATUS current
        DESCRIPTION
            "Feature type. The number 3 means sampling at a fixed interval and sampling for fixed and random packets with a sampling ratio less than 10000 in the behavior."
        ::= { hwXQoSUnsupportedFeatureAlarmEntry 2 }

--end add by guanqingyu

    hwXQoSBUMReplicationAlarmObjects OBJECT IDENTIFIER ::= { hwXQoSObjects 110 }

    hwXQoSBUMReplicationAlarmTable OBJECT-TYPE
        SYNTAX SEQUENCE OF HwXQoSBUMReplicationAlarmEntry
        MAX-ACCESS not-accessible
        STATUS current
        DESCRIPTION
            "hwXQoSBUMReplicationAlarmTable"
        ::= { hwXQoSBUMReplicationAlarmObjects 1 }

    hwXQoSBUMReplicationAlarmEntry OBJECT-TYPE
        SYNTAX HwXQoSBUMReplicationAlarmEntry
        MAX-ACCESS not-accessible
        STATUS current
        DESCRIPTION
            "hwXQoSBUMReplicationAlarmEntry"
        INDEX { hwXQoSBUMReplicationAlarmSlotId, hwXQoSBUMReplicationAlarmChipId }
        ::= { hwXQoSBUMReplicationAlarmTable 1 }

    HwXQoSBUMReplicationAlarmEntry ::=
        SEQUENCE {
            hwXQoSBUMReplicationAlarmSlotId
                Integer32,
            hwXQoSBUMReplicationAlarmChipId
                Integer32
                }

    hwXQoSBUMReplicationAlarmSlotId OBJECT-TYPE
        SYNTAX Integer32
        MAX-ACCESS read-only
        STATUS current
        DESCRIPTION
            "Slot ID."
        ::= { hwXQoSBUMReplicationAlarmEntry 1 }

    hwXQoSBUMReplicationAlarmChipId OBJECT-TYPE
        SYNTAX Integer32
        MAX-ACCESS read-only
        STATUS current
        DESCRIPTION
            "Chip ID."
        ::= { hwXQoSBUMReplicationAlarmEntry 2 }

    hwXQoSVlanStormSuppressAlarmObjects OBJECT IDENTIFIER ::= { hwXQoSObjects 111 }

    hwXQoSVlanStormSuppressAlarmTable OBJECT-TYPE
        SYNTAX SEQUENCE OF HwXQoSVlanStormSuppressAlarmEntry
        MAX-ACCESS not-accessible
        STATUS current
        DESCRIPTION
            "hwXQoSVlanStormSuppressAlarmTable"
        ::= { hwXQoSVlanStormSuppressAlarmObjects 1 }

    hwXQoSVlanStormSuppressAlarmEntry OBJECT-TYPE
        SYNTAX HwXQoSVlanStormSuppressAlarmEntry
        MAX-ACCESS not-accessible
        STATUS current
        DESCRIPTION
            "hwXQoSVlanStormSuppressAlarmEntry"
        INDEX { hwXQoSVlanStormSuppressAlarmVlanid}
        ::= { hwXQoSVlanStormSuppressAlarmTable 1 }

    HwXQoSVlanStormSuppressAlarmEntry ::=
        SEQUENCE {
        hwXQoSVlanStormSuppressAlarmVlanid
                Integer32
                }

    hwXQoSVlanStormSuppressAlarmVlanid OBJECT-TYPE
        SYNTAX Integer32
        MAX-ACCESS read-only
        STATUS current
        DESCRIPTION
            "segment member vlanid."
        ::= { hwXQoSVlanStormSuppressAlarmEntry 1 }

    hwXQoSBDStormSuppressAlarmObjects OBJECT IDENTIFIER ::= { hwXQoSObjects 112 }

    hwXQoSBDStormSuppressAlarmTable OBJECT-TYPE
        SYNTAX SEQUENCE OF HwXQoSBDStormSuppressAlarmEntry
        MAX-ACCESS not-accessible
        STATUS current
        DESCRIPTION
            "hwXQoSBDStormSuppressAlarmTable"
        ::= { hwXQoSBDStormSuppressAlarmObjects 1 }

    hwXQoSBDStormSuppressAlarmEntry OBJECT-TYPE
        SYNTAX HwXQoSBDStormSuppressAlarmEntry
        MAX-ACCESS not-accessible
        STATUS current
        DESCRIPTION
            "hwXQoSBDStormSuppressAlarmEntry"
        INDEX { hwXQoSBDStormSuppressAlarmBdid}
        ::= { hwXQoSBDStormSuppressAlarmTable 1 }

    HwXQoSBDStormSuppressAlarmEntry ::=
        SEQUENCE {
        hwXQoSBDStormSuppressAlarmBdid
                Integer32
                }

    hwXQoSBDStormSuppressAlarmBdid OBJECT-TYPE
        SYNTAX Integer32
        MAX-ACCESS read-only
        STATUS current
        DESCRIPTION
            "segment member bdid."
        ::= { hwXQoSBDStormSuppressAlarmEntry 1 }


    hwXQoSRedirectNextHopEventLogObjects OBJECT IDENTIFIER ::= { hwXQoSObjects 113 }

    hwXQoSRedirectNextHopEventLogTable OBJECT-TYPE
        SYNTAX SEQUENCE OF HwXQoSRedirectNextHopEventLogEntry
        MAX-ACCESS not-accessible
        STATUS current
        DESCRIPTION
            "hwXQoSRedirectNextHopEventLogTable"
        ::= { hwXQoSRedirectNextHopEventLogObjects 1 }

    hwXQoSRedirectNextHopEventLogEntry OBJECT-TYPE
        SYNTAX HwXQoSRedirectNextHopEventLogEntry
        MAX-ACCESS not-accessible
        STATUS current
        DESCRIPTION
            "hwXQoSRedirectNextHopEventLogEntry"
        INDEX { hwXQoSRedirectNextHopEventLogSlotId, hwXQoSRedirectNextHopEventLogRdrType, hwXQoSRedirectNextHopEventLogIpAddress }
        ::= { hwXQoSRedirectNextHopEventLogTable 1 }

    HwXQoSRedirectNextHopEventLogEntry ::=
        SEQUENCE {
            hwXQoSRedirectNextHopEventLogSlotId
                OCTET STRING,
            hwXQoSRedirectNextHopEventLogRdrType
                OCTET STRING,
            hwXQoSRedirectNextHopEventLogIpAddress
                OCTET STRING,
            hwXQoSRedirectNextHopEventLogBehaviorName
                OCTET STRING
                }

    hwXQoSRedirectNextHopEventLogSlotId OBJECT-TYPE
        SYNTAX OCTET STRING (SIZE (1..128))
        MAX-ACCESS read-only
        STATUS current
        DESCRIPTION
            "Slot Id."
        ::= { hwXQoSRedirectNextHopEventLogEntry 1 }

    hwXQoSRedirectNextHopEventLogRdrType OBJECT-TYPE
        SYNTAX OCTET STRING (SIZE (1..16))
        MAX-ACCESS read-only
        STATUS current
        DESCRIPTION
            "Redirect Type."
        ::= { hwXQoSRedirectNextHopEventLogEntry 2 }

    hwXQoSRedirectNextHopEventLogIpAddress OBJECT-TYPE
        SYNTAX OCTET STRING (SIZE (1..128))
        MAX-ACCESS read-only
        STATUS current
        DESCRIPTION
            "Ip Address."
        ::= { hwXQoSRedirectNextHopEventLogEntry 3 }

    hwXQoSRedirectNextHopEventLogBehaviorName OBJECT-TYPE
        SYNTAX OCTET STRING (SIZE (1..128))
        MAX-ACCESS read-only
        STATUS current
        DESCRIPTION
            "Behavior Name."
        ::= { hwXQoSRedirectNextHopEventLogEntry 4 }


    hwXQoSInterfaceDownRedirectNextHopInvalidAlarmObjects OBJECT IDENTIFIER ::= { hwXQoSObjects 114 }

    hwXQoSInterfaceDownRedirectNextHopInvalidAlarmTable OBJECT-TYPE
        SYNTAX SEQUENCE OF HwXQoSInterfaceDownRedirectNextHopInvalidAlarmEntry
        MAX-ACCESS not-accessible
        STATUS current
        DESCRIPTION
            "hwXQoSInterfaceDownRedirectNextHopInvalidAlarmTable"
        ::= { hwXQoSInterfaceDownRedirectNextHopInvalidAlarmObjects 1 }

    hwXQoSInterfaceDownRedirectNextHopInvalidAlarmEntry OBJECT-TYPE
        SYNTAX HwXQoSInterfaceDownRedirectNextHopInvalidAlarmEntry
        MAX-ACCESS not-accessible
        STATUS current
        DESCRIPTION
            "hwXQoSInterfaceDownRedirectNextHopInvalidAlarmEntry"
        INDEX { hwXQoSInterfaceDownRedirectNextHopInvalidAlarmRdrType, hwXQoSInterfaceDownRedirectNextHopInvalidAlarmSlotID, hwXQoSInterfaceDownRedirectNextHopInvalidAlarmInterface }
        ::= { hwXQoSInterfaceDownRedirectNextHopInvalidAlarmTable 1 }

    HwXQoSInterfaceDownRedirectNextHopInvalidAlarmEntry ::=
        SEQUENCE {
            hwXQoSInterfaceDownRedirectNextHopInvalidAlarmRdrType
                OCTET STRING,
            hwXQoSInterfaceDownRedirectNextHopInvalidAlarmSlotID
                OCTET STRING,
            hwXQoSInterfaceDownRedirectNextHopInvalidAlarmInterface
                OCTET STRING,
            hwXQoSInterfaceDownRedirectNextHopInvalidAlarmBehaviorName
                OCTET STRING
                }

    hwXQoSInterfaceDownRedirectNextHopInvalidAlarmRdrType OBJECT-TYPE
        SYNTAX OCTET STRING (SIZE (1..16))
        MAX-ACCESS read-only
        STATUS current
        DESCRIPTION
            "Redirect type of the Behavior when the interface goes down and the redirection next hop becomes invalid."
        ::= { hwXQoSInterfaceDownRedirectNextHopInvalidAlarmEntry 1 }

    hwXQoSInterfaceDownRedirectNextHopInvalidAlarmSlotID OBJECT-TYPE
        SYNTAX OCTET STRING (SIZE (1..128))
        MAX-ACCESS read-only
        STATUS current
        DESCRIPTION
            "The slot configured with storm control."
        ::= { hwXQoSInterfaceDownRedirectNextHopInvalidAlarmEntry 2 }

    hwXQoSInterfaceDownRedirectNextHopInvalidAlarmInterface OBJECT-TYPE
        SYNTAX OCTET STRING (SIZE (1..511))
        MAX-ACCESS read-only
        STATUS current
        DESCRIPTION
            "Name of the interface when the interface goes down and the redirection next hop becomes invalid."
        ::= { hwXQoSInterfaceDownRedirectNextHopInvalidAlarmEntry 3 }

    hwXQoSInterfaceDownRedirectNextHopInvalidAlarmBehaviorName OBJECT-TYPE
        SYNTAX OCTET STRING (SIZE (1..128))
        MAX-ACCESS read-only
        STATUS current
        DESCRIPTION
            "Behavior ID of the Behavior when the interface goes down and the redirection next hop becomes invalid."
        ::= { hwXQoSInterfaceDownRedirectNextHopInvalidAlarmEntry 4 }


    hwXQoSUserQueueApplyPirExhaustionAlarmObjects OBJECT IDENTIFIER ::= { hwXQoSObjects 117 }

    hwXQoSUserQueueApplyPirExhaustionAlarmTable OBJECT-TYPE
        SYNTAX SEQUENCE OF HwXQoSUserQueueApplyPirExhaustionAlarmEntry
        MAX-ACCESS not-accessible
        STATUS current
        DESCRIPTION
            "hwXQoSUserQueueApplyPirExhaustionAlarmTable"
        ::= { hwXQoSUserQueueApplyPirExhaustionAlarmObjects 1 }

    hwXQoSUserQueueApplyPirExhaustionAlarmEntry OBJECT-TYPE
        SYNTAX HwXQoSUserQueueApplyPirExhaustionAlarmEntry
        MAX-ACCESS not-accessible
        STATUS current
        DESCRIPTION
            "hwXQoSUserQueueApplyPirExhaustionAlarmEntry"
        INDEX { hwXQoSUserQueueApplyPirExhaustionAlarmSlotId, hwXQoSUserQueueApplyPirExhaustionAlarmTmChipId, hwXQoSUserQueueApplyPirExhaustionAlarmPoolIndex }
        ::= { hwXQoSUserQueueApplyPirExhaustionAlarmTable 1 }

    HwXQoSUserQueueApplyPirExhaustionAlarmEntry ::=
        SEQUENCE {
            hwXQoSUserQueueApplyPirExhaustionAlarmSlotId
                OCTET STRING,
            hwXQoSUserQueueApplyPirExhaustionAlarmTmChipId
                Unsigned32,
            hwXQoSUserQueueApplyPirExhaustionAlarmPoolIndex
                Unsigned32
        }

    hwXQoSUserQueueApplyPirExhaustionAlarmSlotId OBJECT-TYPE
        SYNTAX OCTET STRING (SIZE (1..128))
        MAX-ACCESS read-only
        STATUS current
        DESCRIPTION
            "The slot id of the device."
        ::= { hwXQoSUserQueueApplyPirExhaustionAlarmEntry 1 }

    hwXQoSUserQueueApplyPirExhaustionAlarmTmChipId OBJECT-TYPE
        SYNTAX Unsigned32
        MAX-ACCESS read-only
        STATUS current
        DESCRIPTION
        "The information of the chip."
        ::= { hwXQoSUserQueueApplyPirExhaustionAlarmEntry 2 }

    hwXQoSUserQueueApplyPirExhaustionAlarmPoolIndex OBJECT-TYPE
        SYNTAX Unsigned32
        MAX-ACCESS read-only
        STATUS current
        DESCRIPTION
        "Resource pool index"
        ::= { hwXQoSUserQueueApplyPirExhaustionAlarmEntry 3 }


    hwXQoSUserQueueApplyPirPreAlarmObjects OBJECT IDENTIFIER ::= { hwXQoSObjects 118 }

    hwXQoSUserQueueApplyPirPreAlarmTable OBJECT-TYPE
        SYNTAX SEQUENCE OF HwXQoSUserQueueApplyPirPreAlarmEntry
        MAX-ACCESS not-accessible
        STATUS current
        DESCRIPTION
            "hwXQoSUserQueueApplyPirPreAlarmTable"
        ::= { hwXQoSUserQueueApplyPirPreAlarmObjects 1 }

    hwXQoSUserQueueApplyPirPreAlarmEntry OBJECT-TYPE
        SYNTAX HwXQoSUserQueueApplyPirPreAlarmEntry
        MAX-ACCESS not-accessible
        STATUS current
        DESCRIPTION
            "hwXQoSUserQueueApplyPirPreAlarmEntry"
        INDEX { hwXQoSUserQueueApplyPirPreAlarmSlotId, hwXQoSUserQueueApplyPirPreAlarmTmChipId, hwXQoSUserQueueApplyPirPreAlarmPoolIndex }
        ::= { hwXQoSUserQueueApplyPirPreAlarmTable 1 }

    HwXQoSUserQueueApplyPirPreAlarmEntry ::=
        SEQUENCE {
            hwXQoSUserQueueApplyPirPreAlarmSlotId
                OCTET STRING,
            hwXQoSUserQueueApplyPirPreAlarmTmChipId
                Unsigned32,
            hwXQoSUserQueueApplyPirPreAlarmPoolIndex
                Unsigned32
        }

    hwXQoSUserQueueApplyPirPreAlarmSlotId OBJECT-TYPE
        SYNTAX OCTET STRING (SIZE (1..128))
        MAX-ACCESS read-only
        STATUS current
        DESCRIPTION
            "The slot id of the device."
        ::= { hwXQoSUserQueueApplyPirPreAlarmEntry 1 }

    hwXQoSUserQueueApplyPirPreAlarmTmChipId OBJECT-TYPE
        SYNTAX Unsigned32
        MAX-ACCESS read-only
        STATUS current
        DESCRIPTION
            "The information of the chip."
        ::= { hwXQoSUserQueueApplyPirPreAlarmEntry 2 }

    hwXQoSUserQueueApplyPirPreAlarmPoolIndex OBJECT-TYPE
        SYNTAX Unsigned32
        MAX-ACCESS read-only
        STATUS current
        DESCRIPTION
            "Resource pool index"
        ::= { hwXQoSUserQueueApplyPirPreAlarmEntry 3 }


    hwXQoSUserQueuePirAdjustAlarmObjects OBJECT IDENTIFIER ::= { hwXQoSObjects 119 }

    hwXQoSUserQueuePirAdjustAlarmTable OBJECT-TYPE
        SYNTAX SEQUENCE OF HwXQoSUserQueuePirAdjustAlarmEntry
        MAX-ACCESS not-accessible
        STATUS current
        DESCRIPTION
            "hwXQoSUserQueuePirAdjustAlarmTable"
        ::= { hwXQoSUserQueuePirAdjustAlarmObjects 1 }

    hwXQoSUserQueuePirAdjustAlarmEntry OBJECT-TYPE
        SYNTAX HwXQoSUserQueuePirAdjustAlarmEntry
        MAX-ACCESS not-accessible
        STATUS current
        DESCRIPTION
            "hwXQoSUserQueuePirAdjustAlarmEntry"
        INDEX { hwXQoSUserQueuePirAdjustAlarmSlotId, hwXQoSUserQueuePirAdjustAlarmTmChipId, hwXQoSUserQueuePirAdjustAlarmPoolIndex }
        ::= { hwXQoSUserQueuePirAdjustAlarmTable 1 }

    HwXQoSUserQueuePirAdjustAlarmEntry ::=
        SEQUENCE {
            hwXQoSUserQueuePirAdjustAlarmSlotId
                OCTET STRING,
            hwXQoSUserQueuePirAdjustAlarmTmChipId
                Unsigned32,
            hwXQoSUserQueuePirAdjustAlarmPoolIndex
                Unsigned32
        }

    hwXQoSUserQueuePirAdjustAlarmSlotId OBJECT-TYPE
        SYNTAX OCTET STRING (SIZE (1..128))
        MAX-ACCESS read-only
        STATUS current
        DESCRIPTION
            "The slot id of the device."
        ::= { hwXQoSUserQueuePirAdjustAlarmEntry 1 }

    hwXQoSUserQueuePirAdjustAlarmTmChipId OBJECT-TYPE
        SYNTAX Unsigned32
        MAX-ACCESS read-only
        STATUS current
        DESCRIPTION
            "The information of the chip."
        ::= { hwXQoSUserQueuePirAdjustAlarmEntry 2 }

    hwXQoSUserQueuePirAdjustAlarmPoolIndex OBJECT-TYPE
        SYNTAX Unsigned32
        MAX-ACCESS read-only
        STATUS current
        DESCRIPTION
            "Resource pool index"
        ::= { hwXQoSUserQueuePirAdjustAlarmEntry 3 }

--BEGIN
    hwXQoSUnsupportedActionAlarmObjects OBJECT IDENTIFIER ::= { hwXQoSObjects 126 }

    hwXQoSUnsupportedActionAlarmTable OBJECT-TYPE
        SYNTAX SEQUENCE OF HwXQoSUnsupportedActionAlarmEntry
        MAX-ACCESS not-accessible
        STATUS current
        DESCRIPTION
            "hwXQoSUnsupportedActionAlarmTable"
        ::= { hwXQoSUnsupportedActionAlarmObjects 1 }

    hwXQoSUnsupportedActionAlarmEntry OBJECT-TYPE
        SYNTAX HwXQoSUnsupportedActionAlarmEntry
        MAX-ACCESS not-accessible
        STATUS current
        DESCRIPTION
            "hwXQoSUnsupportedActionAlarmEntry"
        INDEX { hwXQoSUnsupportedActionAlarmSlotId, hwXQoSUnsupportedActionAlarmActionName, hwXQoSUnsupportedActionAlarmDirection }
        ::= { hwXQoSUnsupportedActionAlarmTable 1 }

    HwXQoSUnsupportedActionAlarmEntry ::=
        SEQUENCE {
            hwXQoSUnsupportedActionAlarmSlotId
                OCTET STRING,
            hwXQoSUnsupportedActionAlarmActionName
                OCTET STRING,
            hwXQoSUnsupportedActionAlarmDirection
                PolicyDirectionType
        }

    hwXQoSUnsupportedActionAlarmSlotId OBJECT-TYPE
        SYNTAX OCTET STRING (SIZE (1..128))
        MAX-ACCESS accessible-for-notify
        STATUS current
        DESCRIPTION
            "The slot id of the device."
        ::= { hwXQoSUnsupportedActionAlarmEntry 1 }

    hwXQoSUnsupportedActionAlarmActionName OBJECT-TYPE
        SYNTAX OCTET STRING (SIZE (1..128))
        MAX-ACCESS accessible-for-notify
        STATUS current
        DESCRIPTION
            "The information of the unsupported action."
        ::= { hwXQoSUnsupportedActionAlarmEntry 2 }

    hwXQoSUnsupportedActionAlarmDirection OBJECT-TYPE
        SYNTAX PolicyDirectionType
        MAX-ACCESS accessible-for-notify
        STATUS current
        DESCRIPTION
            "The direction of the policy apply."
        ::= { hwXQoSUnsupportedActionAlarmEntry 3 }
--END
--BEGIN
    hwXQoSCarBindwidthExceedChipLimitAlarmObjects OBJECT IDENTIFIER ::= { hwXQoSObjects 128 }

    hwXQoSCarBindwidthExceedChipLimitAlarmTable OBJECT-TYPE
        SYNTAX SEQUENCE OF HwXQoSCarBindwidthExceedChipLimitAlarmEntry
        MAX-ACCESS not-accessible
        STATUS current
        DESCRIPTION
            "hwXQoSCarBindwidthExceedChipLimitAlarmTable"
        ::= { hwXQoSCarBindwidthExceedChipLimitAlarmObjects 1 }

    hwXQoSCarBindwidthExceedChipLimitAlarmEntry OBJECT-TYPE
        SYNTAX HwXQoSCarBindwidthExceedChipLimitAlarmEntry
        MAX-ACCESS not-accessible
        STATUS current
        DESCRIPTION
            "hwXQoSCarBindwidthExceedChipLimitAlarmEntry"
        INDEX { hwXQoSCarBindwidthExceedChipLimitAlarmSlotId, hwXQoSCarBindwidthExceedChipLimitAlarmCarType }
        ::= { hwXQoSCarBindwidthExceedChipLimitAlarmTable 1 }

    HwXQoSCarBindwidthExceedChipLimitAlarmEntry ::=
        SEQUENCE {
            hwXQoSCarBindwidthExceedChipLimitAlarmSlotId
                OCTET STRING,
            hwXQoSCarBindwidthExceedChipLimitAlarmCarType
                OCTET STRING,
            hwXQoSCarBindwidthExceedChipLimitAlarmCir
                Unsigned32,
            hwXQoSCarBindwidthExceedChipLimitAlarmPir
                Unsigned32,
            hwXQoSCarBindwidthExceedChipLimitAlarmMaxRateLimit
                Unsigned32,
            hwXQoSCarBindwidthExceedChipLimitAlarmIsPercent
                OCTET STRING
        }

    hwXQoSCarBindwidthExceedChipLimitAlarmSlotId OBJECT-TYPE
        SYNTAX OCTET STRING (SIZE (1..128))
        MAX-ACCESS accessible-for-notify
        STATUS current
        DESCRIPTION
            "The slot id of the device."
        ::= { hwXQoSCarBindwidthExceedChipLimitAlarmEntry 1 }

    hwXQoSCarBindwidthExceedChipLimitAlarmCarType OBJECT-TYPE
        SYNTAX OCTET STRING (SIZE (1..128))
        MAX-ACCESS accessible-for-notify
        STATUS current
        DESCRIPTION
            "The type of CAR."
        ::= { hwXQoSCarBindwidthExceedChipLimitAlarmEntry 2 }

    hwXQoSCarBindwidthExceedChipLimitAlarmCir OBJECT-TYPE
        SYNTAX Unsigned32
        MAX-ACCESS accessible-for-notify
        STATUS current
        DESCRIPTION
            "Committed Information Rate."
        ::= { hwXQoSCarBindwidthExceedChipLimitAlarmEntry 3 }

    hwXQoSCarBindwidthExceedChipLimitAlarmPir OBJECT-TYPE
        SYNTAX Unsigned32
        MAX-ACCESS accessible-for-notify
        STATUS current
        DESCRIPTION
            "Peak Information Rate."
        ::= { hwXQoSCarBindwidthExceedChipLimitAlarmEntry 4 }

    hwXQoSCarBindwidthExceedChipLimitAlarmMaxRateLimit OBJECT-TYPE
        SYNTAX Unsigned32
        MAX-ACCESS accessible-for-notify
        STATUS current
        DESCRIPTION
            "Maximum rate limiting capability of the chip."
        ::= { hwXQoSCarBindwidthExceedChipLimitAlarmEntry 5 }

    hwXQoSCarBindwidthExceedChipLimitAlarmIsPercent OBJECT-TYPE
        SYNTAX OCTET STRING (SIZE (1..128))
        MAX-ACCESS accessible-for-notify
        STATUS current
        DESCRIPTION
            "Is percent mode or not"
        ::= { hwXQoSCarBindwidthExceedChipLimitAlarmEntry 6 }
--END
--BEGIN
    hwXQoSModeChannelOverEthBnBwdAlarmObjects OBJECT IDENTIFIER ::= { hwXQoSObjects 129 }

    hwXQoSModeChannelOverEthBnBwdAlarmTable OBJECT-TYPE
        SYNTAX SEQUENCE OF HwXQoSModeChannelOverEthBnBwdAlarmEntry
        MAX-ACCESS not-accessible
        STATUS current
        DESCRIPTION
            "hwXQoSModeChannelOverEthBnBwdAlarmTable"
        ::= { hwXQoSModeChannelOverEthBnBwdAlarmObjects 1 }

    hwXQoSModeChannelOverEthBnBwdAlarmEntry OBJECT-TYPE
        SYNTAX HwXQoSModeChannelOverEthBnBwdAlarmEntry
        MAX-ACCESS not-accessible
        STATUS current
        DESCRIPTION
            "hwXQoSModeChannelOverEthBnBwdAlarmEntry"
        INDEX { hwXQoSModeChannelOverEthBnBwdAlarmGroupName }
        ::= { hwXQoSModeChannelOverEthBnBwdAlarmTable 1 }

    HwXQoSModeChannelOverEthBnBwdAlarmEntry ::=
        SEQUENCE {
            hwXQoSModeChannelOverEthBnBwdAlarmGroupName
                OCTET STRING,
            hwXQoSModeChannelOverEthBnBwdAlarmEthBnSubInterface
                OCTET STRING
        }

    hwXQoSModeChannelOverEthBnBwdAlarmGroupName OBJECT-TYPE
        SYNTAX OCTET STRING (SIZE (1..32))
        MAX-ACCESS accessible-for-notify
        STATUS current
        DESCRIPTION
            "The eth-bn group."
        ::= { hwXQoSModeChannelOverEthBnBwdAlarmEntry 1 }

    hwXQoSModeChannelOverEthBnBwdAlarmEthBnSubInterface OBJECT-TYPE
        SYNTAX OCTET STRING (SIZE (1..511))
        MAX-ACCESS accessible-for-notify
        STATUS current
        DESCRIPTION
            "The main interface of the interface added to eth-bn group."
        ::= { hwXQoSModeChannelOverEthBnBwdAlarmEntry 2 }
--END

    hwXACLEPGRuleAlarmObjects OBJECT IDENTIFIER ::= { hwXQoSObjects 130 }

    hwXACLEPGRuleAlarmTable OBJECT-TYPE
        SYNTAX SEQUENCE OF HwXACLEPGRuleAlarmEntry
        MAX-ACCESS not-accessible
        STATUS current
        DESCRIPTION
            "hwXACLEPGRuleAlarmTable"
        ::= { hwXACLEPGRuleAlarmObjects 1 }

    hwXACLEPGRuleAlarmEntry OBJECT-TYPE
        SYNTAX HwXACLEPGRuleAlarmEntry
        MAX-ACCESS not-accessible
        STATUS current
        DESCRIPTION
            "hwXACLEPGRuleAlarmEntry"
        INDEX { hwXACLEPGRuleAlarmSlotid, hwXACLEPGRuleAlarmPolicy, hwXACLEPGRuleAlarmClassifier, hwXACLEPGRuleAlarmPriority }
        ::= { hwXACLEPGRuleAlarmTable 1 }

    HwXACLEPGRuleAlarmEntry ::=
        SEQUENCE {
            hwXACLEPGRuleAlarmSlotid
                OCTET STRING,
            hwXACLEPGRuleAlarmPolicy
                OCTET STRING,
            hwXACLEPGRuleAlarmClassifier
                OCTET STRING,
            hwXACLEPGRuleAlarmPriority
                OCTET STRING,
            hwXACLEPGRuleAlarmSourceSegmentId
                OCTET STRING,
            hwXACLEPGRuleAlarmDestinationSegmentId
                OCTET STRING,
            hwXACLEPGRuleAlarmProtocol
                OCTET STRING,
            hwXACLEPGRuleAlarmSourceport
                OCTET STRING,
            hwXACLEPGRuleAlarmDestinationport
                OCTET STRING
                }


    hwXACLEPGRuleAlarmSlotid OBJECT-TYPE
        SYNTAX OCTET STRING
        MAX-ACCESS read-only
        STATUS current
        DESCRIPTION
            "slot id."
        ::= { hwXACLEPGRuleAlarmEntry 1 }
    hwXACLEPGRuleAlarmPolicy OBJECT-TYPE
        SYNTAX OCTET STRING
        MAX-ACCESS read-only
        STATUS current
        DESCRIPTION
            "policy."
        ::= { hwXACLEPGRuleAlarmEntry 2 }
    hwXACLEPGRuleAlarmClassifier OBJECT-TYPE
        SYNTAX OCTET STRING
        MAX-ACCESS read-only
        STATUS current
        DESCRIPTION
            "classifier."
        ::= { hwXACLEPGRuleAlarmEntry 3 }
    hwXACLEPGRuleAlarmPriority OBJECT-TYPE
        SYNTAX OCTET STRING
        MAX-ACCESS read-only
        STATUS current
        DESCRIPTION
            "classifier."
        ::= { hwXACLEPGRuleAlarmEntry 4 }
    hwXACLEPGRuleAlarmSourceSegmentId OBJECT-TYPE
        SYNTAX OCTET STRING
        MAX-ACCESS read-only
        STATUS current
        DESCRIPTION
            "source segment id."
        ::= { hwXACLEPGRuleAlarmEntry 5 }
    hwXACLEPGRuleAlarmDestinationSegmentId OBJECT-TYPE
        SYNTAX OCTET STRING
        MAX-ACCESS read-only
        STATUS current
        DESCRIPTION
            "destination segment id."
        ::= { hwXACLEPGRuleAlarmEntry 6 }
    hwXACLEPGRuleAlarmProtocol OBJECT-TYPE
        SYNTAX OCTET STRING
        MAX-ACCESS read-only
        STATUS current
        DESCRIPTION
            "protocol."
        ::= { hwXACLEPGRuleAlarmEntry 7 }
    hwXACLEPGRuleAlarmSourceport OBJECT-TYPE
        SYNTAX OCTET STRING
        MAX-ACCESS read-only
        STATUS current
        DESCRIPTION
            "source-port."
        ::= { hwXACLEPGRuleAlarmEntry 8 }
    hwXACLEPGRuleAlarmDestinationport OBJECT-TYPE
        SYNTAX OCTET STRING
        MAX-ACCESS read-only
        STATUS current
        DESCRIPTION
            "destination-port."
        ::= { hwXACLEPGRuleAlarmEntry 9 }
--BEGIN
    hwXQoSBoardHQoSFailAlarmObjects OBJECT IDENTIFIER ::= { hwXQoSObjects 131 }

    hwXQoSBoardHQoSFailAlarmTable OBJECT-TYPE
        SYNTAX SEQUENCE OF HwXQoSBoardHQoSFailAlarmEntry
        MAX-ACCESS not-accessible
        STATUS current
        DESCRIPTION
            "hwXQoSBoardHQoSFailAlarmTable"
        ::= { hwXQoSBoardHQoSFailAlarmObjects 1 }

    hwXQoSBoardHQoSFailAlarmEntry OBJECT-TYPE
        SYNTAX HwXQoSBoardHQoSFailAlarmEntry
        MAX-ACCESS not-accessible
        STATUS current
        DESCRIPTION
            "hwXQoSBoardHQoSFailAlarmEntry"
        INDEX { hwXQoSBoardHQoSFailAlarmServiceType, hwXQoSBoardHQoSFailAlarmSlotId, hwXQoSBoardHQoSFailAlarmReasonId }
        ::= { hwXQoSBoardHQoSFailAlarmTable 1 }

    HwXQoSBoardHQoSFailAlarmEntry ::=
        SEQUENCE {
            hwXQoSBoardHQoSFailAlarmServiceType
                OCTET STRING,
            hwXQoSBoardHQoSFailAlarmSlotId
                OCTET STRING,
            hwXQoSBoardHQoSFailAlarmReasonId
                Unsigned32,
            hwXQoSBoardHQoSFailAlarmReasonDescription
                OCTET STRING
        }

    hwXQoSBoardHQoSFailAlarmServiceType OBJECT-TYPE
        SYNTAX OCTET STRING (SIZE (1..127))
        MAX-ACCESS accessible-for-notify
        STATUS current
        DESCRIPTION
            "Indicates the HQoS service corresponding to the alarm."
        ::= { hwXQoSBoardHQoSFailAlarmEntry 1 }

    hwXQoSBoardHQoSFailAlarmSlotId OBJECT-TYPE
        SYNTAX OCTET STRING (SIZE (1..31))
        MAX-ACCESS accessible-for-notify
        STATUS current
        DESCRIPTION
            "The ID of slot."
        ::= { hwXQoSBoardHQoSFailAlarmEntry 2 }

    hwXQoSBoardHQoSFailAlarmReasonId OBJECT-TYPE
        SYNTAX Unsigned32
        MAX-ACCESS accessible-for-notify
        STATUS current
        DESCRIPTION
            "The ID of alarm reason."
        ::= { hwXQoSBoardHQoSFailAlarmEntry 3 }

    hwXQoSBoardHQoSFailAlarmReasonDescription OBJECT-TYPE
        SYNTAX OCTET STRING (SIZE (1..511))
        MAX-ACCESS accessible-for-notify
        STATUS current
        DESCRIPTION
            "The description of the alarm cause."
        ::= { hwXQoSBoardHQoSFailAlarmEntry 4 }
--END
--BEGIN
    hwXQoSInterfaceHQoSFailAlarmObjects OBJECT IDENTIFIER ::= { hwXQoSObjects 132 }

    hwXQoSInterfaceHQoSFailAlarmTable OBJECT-TYPE
        SYNTAX SEQUENCE OF HwXQoSInterfaceHQoSFailAlarmEntry
        MAX-ACCESS not-accessible
        STATUS current
        DESCRIPTION
            "hwXQoSInterfaceHQoSFailAlarmTable"
        ::= { hwXQoSInterfaceHQoSFailAlarmObjects 1 }

    hwXQoSInterfaceHQoSFailAlarmEntry OBJECT-TYPE
        SYNTAX HwXQoSInterfaceHQoSFailAlarmEntry
        MAX-ACCESS not-accessible
        STATUS current
        DESCRIPTION
            "hwXQoSInterfaceHQoSFailAlarmEntry"
        INDEX { hwXQoSInterfaceHQoSFailAlarmServiceType, hwXQoSInterfaceHQoSFailAlarmSlotId, hwXQoSInterfaceHQoSFailAlarmInterfaceName, hwXQoSInterfaceHQoSFailAlarmReasonId }
        ::= { hwXQoSInterfaceHQoSFailAlarmTable 1 }

    HwXQoSInterfaceHQoSFailAlarmEntry ::=
        SEQUENCE {
            hwXQoSInterfaceHQoSFailAlarmServiceType
                OCTET STRING,
            hwXQoSInterfaceHQoSFailAlarmSlotId
                OCTET STRING,
            hwXQoSInterfaceHQoSFailAlarmInterfaceName
                OCTET STRING,
            hwXQoSInterfaceHQoSFailAlarmReasonId
                Unsigned32,
            hwXQoSInterfaceHQoSFailAlarmReasonDescription
                OCTET STRING
        }

    hwXQoSInterfaceHQoSFailAlarmServiceType OBJECT-TYPE
        SYNTAX OCTET STRING (SIZE (1..127))
        MAX-ACCESS accessible-for-notify
        STATUS current
        DESCRIPTION
            "Indicates the HQoS service corresponding to the alarm."
        ::= { hwXQoSInterfaceHQoSFailAlarmEntry 1 }

    hwXQoSInterfaceHQoSFailAlarmSlotId OBJECT-TYPE
        SYNTAX OCTET STRING (SIZE (1..31))
        MAX-ACCESS accessible-for-notify
        STATUS current
        DESCRIPTION
            "The ID of slot."
        ::= { hwXQoSInterfaceHQoSFailAlarmEntry 2 }

    hwXQoSInterfaceHQoSFailAlarmInterfaceName OBJECT-TYPE
        SYNTAX OCTET STRING (SIZE (1..511))
        MAX-ACCESS accessible-for-notify
        STATUS current
        DESCRIPTION
            "The name of interface."
        ::= { hwXQoSInterfaceHQoSFailAlarmEntry 3 }

    hwXQoSInterfaceHQoSFailAlarmReasonId OBJECT-TYPE
        SYNTAX Unsigned32
        MAX-ACCESS accessible-for-notify
        STATUS current
        DESCRIPTION
            "The ID of alarm reason."
        ::= { hwXQoSInterfaceHQoSFailAlarmEntry 4 }

    hwXQoSInterfaceHQoSFailAlarmReasonDescription OBJECT-TYPE
        SYNTAX OCTET STRING (SIZE (1..511))
        MAX-ACCESS accessible-for-notify
        STATUS current
        DESCRIPTION
            "The description of the alarm cause."
        ::= { hwXQoSInterfaceHQoSFailAlarmEntry 5 }
--END
--BEGIN
    hwXQoSReceivedMultiPauseFrameInterfaceDownAlarmObjects OBJECT IDENTIFIER ::= { hwXQoSObjects 133 }

    hwXQoSReceivedMultiPauseFrameInterfaceDownAlarmTable OBJECT-TYPE
        SYNTAX SEQUENCE OF HwXQoSReceivedMultiPauseFrameInterfaceDownAlarmEntry
        MAX-ACCESS not-accessible
        STATUS current
        DESCRIPTION
            "hwXQoSReceivedMultiPauseFrameInterfaceDownAlarmTable"
        ::= { hwXQoSReceivedMultiPauseFrameInterfaceDownAlarmObjects 1 }

    hwXQoSReceivedMultiPauseFrameInterfaceDownAlarmEntry OBJECT-TYPE
        SYNTAX HwXQoSReceivedMultiPauseFrameInterfaceDownAlarmEntry
        MAX-ACCESS not-accessible
        STATUS current
        DESCRIPTION
            "hwXQoSReceivedMultiPauseFrameInterfaceDownAlarmEntry"
        INDEX { hwXQoSReceivedMultiPauseFrameInterfaceDownAlarmInterfaceName }
        ::= { hwXQoSReceivedMultiPauseFrameInterfaceDownAlarmTable 1 }

    HwXQoSReceivedMultiPauseFrameInterfaceDownAlarmEntry ::=
        SEQUENCE {
            hwXQoSReceivedMultiPauseFrameInterfaceDownAlarmInterfaceName
                OCTET STRING
        }

    hwXQoSReceivedMultiPauseFrameInterfaceDownAlarmInterfaceName OBJECT-TYPE
        SYNTAX OCTET STRING (SIZE (1..128))
        MAX-ACCESS accessible-for-notify
        STATUS current
        DESCRIPTION
            "Interface name."
        ::= { hwXQoSReceivedMultiPauseFrameInterfaceDownAlarmEntry 1 }
--END
--BEGIN
    hwXQoSTrunkTrafficCongestionAlarmObjects OBJECT IDENTIFIER ::= { hwXQoSObjects 134 }

    hwXQoSTrunkTrafficCongestionAlarmTable OBJECT-TYPE
        SYNTAX SEQUENCE OF HwXQoSTrunkTrafficCongestionAlarmEntry
        MAX-ACCESS not-accessible
        STATUS current
        DESCRIPTION
            "hwXQoSTrunkTrafficCongestionAlarmTable"
        ::= { hwXQoSTrunkTrafficCongestionAlarmObjects 1 }

    hwXQoSTrunkTrafficCongestionAlarmEntry OBJECT-TYPE
        SYNTAX HwXQoSTrunkTrafficCongestionAlarmEntry
        MAX-ACCESS not-accessible
        STATUS current
        DESCRIPTION
            "hwXQoSTrunkTrafficCongestionAlarmEntry"
        INDEX { hwXQoSTrunkTrafficCongestionAlarmTrunkName, hwXQoSTrunkTrafficCongestionAlarmSlotId }
        ::= { hwXQoSTrunkTrafficCongestionAlarmTable 1 }

    HwXQoSTrunkTrafficCongestionAlarmEntry ::=
        SEQUENCE {
            hwXQoSTrunkTrafficCongestionAlarmTrunkName
                OCTET STRING,
            hwXQoSTrunkTrafficCongestionAlarmSlotId
                OCTET STRING
        }

    hwXQoSTrunkTrafficCongestionAlarmTrunkName OBJECT-TYPE
        SYNTAX OCTET STRING (SIZE (1..128))
        MAX-ACCESS accessible-for-notify
        STATUS current
        DESCRIPTION
            "Interface name."
        ::= { hwXQoSTrunkTrafficCongestionAlarmEntry 1 }

    hwXQoSTrunkTrafficCongestionAlarmSlotId OBJECT-TYPE
        SYNTAX OCTET STRING (SIZE (1..31))
        MAX-ACCESS accessible-for-notify
        STATUS current
        DESCRIPTION
            "The ID of slot."
        ::= { hwXQoSTrunkTrafficCongestionAlarmEntry 2 }
--END
--BEGIN
    hwXQoSFwdResourceOverloadObjects OBJECT IDENTIFIER ::= { hwXQoSObjects 135 }

    hwXQoSFwdResourceOverloadTable OBJECT-TYPE
        SYNTAX SEQUENCE OF HwXQoSFwdResourceOverloadEntry
        MAX-ACCESS not-accessible
        STATUS current
        DESCRIPTION
            "hwXQoSFwdResourceOverloadTable"
        ::= { hwXQoSFwdResourceOverloadObjects 1 }

    hwXQoSFwdResourceOverloadEntry OBJECT-TYPE
        SYNTAX HwXQoSFwdResourceOverloadEntry
        MAX-ACCESS not-accessible
        STATUS current
        DESCRIPTION
            "hwXQoSFwdResourceOverloadEntry"
        INDEX { hwXQoSFwdResourceOverloadSlotId, hwXQoSFwdResourceOverloadReasonId }
        ::= { hwXQoSFwdResourceOverloadTable 1 }

    HwXQoSFwdResourceOverloadEntry ::=
        SEQUENCE {
            hwXQoSFwdResourceOverloadSlotId
                OCTET STRING,
            hwXQoSFwdResourceOverloadReasonId
                FwdResourceOverloadType
        }

    hwXQoSFwdResourceOverloadSlotId OBJECT-TYPE
        SYNTAX OCTET STRING (SIZE (1..31))
        MAX-ACCESS accessible-for-notify
        STATUS current
        DESCRIPTION
            "The ID of slot."
        ::= { hwXQoSFwdResourceOverloadEntry 1 }

    hwXQoSFwdResourceOverloadReasonId OBJECT-TYPE
        SYNTAX FwdResourceOverloadType
        MAX-ACCESS accessible-for-notify
        STATUS current
        DESCRIPTION
            "The ID of alarm reason."
        ::= { hwXQoSFwdResourceOverloadEntry 2 }
--END
--BEGIN
    hwXQoSBoardServiceMismatchEventObjects OBJECT IDENTIFIER ::= { hwXQoSObjects 136 }

    hwXQoSBoardServiceMismatchEventTable OBJECT-TYPE
        SYNTAX SEQUENCE OF HwXQoSBoardServiceMismatchEventEntry
        MAX-ACCESS not-accessible
        STATUS current
        DESCRIPTION
            "hwXQoSBoardServiceMismatchEventTable"
        ::= { hwXQoSBoardServiceMismatchEventObjects 1 }

    hwXQoSBoardServiceMismatchEventEntry OBJECT-TYPE
        SYNTAX HwXQoSBoardServiceMismatchEventEntry
        MAX-ACCESS not-accessible
        STATUS current
        DESCRIPTION
            "hwXQoSBoardServiceMismatchEventEntry"
        INDEX { hwXQoSBoardServiceMismatchEventEntityPhysicalIndex, hwXQoSBoardServiceMismatchEventServiceID, hwXQoSBoardServiceMismatchEventEntPhysicalName, hwXQoSBoardServiceMismatchEventServiceName, hwXQoSBoardServiceMismatchEventPrecautions }
        ::= { hwXQoSBoardServiceMismatchEventTable 1 }

    HwXQoSBoardServiceMismatchEventEntry ::=
        SEQUENCE {
            hwXQoSBoardServiceMismatchEventEntityPhysicalIndex
                Unsigned32,
            hwXQoSBoardServiceMismatchEventServiceID
                Unsigned32,
            hwXQoSBoardServiceMismatchEventEntPhysicalName
                OCTET STRING,
            hwXQoSBoardServiceMismatchEventServiceName
                OCTET STRING,
            hwXQoSBoardServiceMismatchEventPrecautions
                OCTET STRING
        }

    hwXQoSBoardServiceMismatchEventEntityPhysicalIndex OBJECT-TYPE
        SYNTAX Unsigned32
        MAX-ACCESS accessible-for-notify
        STATUS current
        DESCRIPTION
            "Index of an entity."
        ::= { hwXQoSBoardServiceMismatchEventEntry 1 }

    hwXQoSBoardServiceMismatchEventServiceID OBJECT-TYPE
        SYNTAX Unsigned32
        MAX-ACCESS accessible-for-notify
        STATUS current
        DESCRIPTION
            "Service ID."
        ::= { hwXQoSBoardServiceMismatchEventEntry 2 }

    hwXQoSBoardServiceMismatchEventEntPhysicalName OBJECT-TYPE
        SYNTAX OCTET STRING (SIZE (1..511))
        MAX-ACCESS accessible-for-notify
        STATUS current
        DESCRIPTION
            "Entity name."
        ::= { hwXQoSBoardServiceMismatchEventEntry 3 }

    hwXQoSBoardServiceMismatchEventServiceName OBJECT-TYPE
        SYNTAX OCTET STRING (SIZE (1..511))
        MAX-ACCESS accessible-for-notify
        STATUS current
        DESCRIPTION
            "Service name."
        ::= { hwXQoSBoardServiceMismatchEventEntry 4 }

    hwXQoSBoardServiceMismatchEventPrecautions OBJECT-TYPE
        SYNTAX OCTET STRING (SIZE (1..511))
        MAX-ACCESS accessible-for-notify
        STATUS current
        DESCRIPTION
            "Precautions."
        ::= { hwXQoSBoardServiceMismatchEventEntry 5 }
--END
--BEGIN
    hwXQoSSlotTrafficCongestionAlarmObjects OBJECT IDENTIFIER ::= { hwXQoSObjects 137 }

    hwXQoSSlotTrafficCongestionAlarmTable OBJECT-TYPE
        SYNTAX SEQUENCE OF HwXQoSSlotTrafficCongestionAlarmEntry
        MAX-ACCESS not-accessible
        STATUS current
        DESCRIPTION
            "hwXQoSSlotTrafficCongestionAlarmTable"
        ::= { hwXQoSSlotTrafficCongestionAlarmObjects 1 }

    hwXQoSSlotTrafficCongestionAlarmEntry OBJECT-TYPE
        SYNTAX HwXQoSSlotTrafficCongestionAlarmEntry
        MAX-ACCESS not-accessible
        STATUS current
        DESCRIPTION
            "hwXQoSSlotTrafficCongestionAlarmEntry"
        INDEX { hwXQoSSlotTrafficCongestionAlarmSlotId }
        ::= { hwXQoSSlotTrafficCongestionAlarmTable 1 }

    HwXQoSSlotTrafficCongestionAlarmEntry ::=
        SEQUENCE {
            hwXQoSSlotTrafficCongestionAlarmSlotId
                OCTET STRING
        }

    hwXQoSSlotTrafficCongestionAlarmSlotId OBJECT-TYPE
        SYNTAX OCTET STRING (SIZE (1..32))
        MAX-ACCESS accessible-for-notify
        STATUS current
        DESCRIPTION
            "The slot id of the device."
        ::= { hwXQoSSlotTrafficCongestionAlarmEntry 1 }
--END
--BEGIN
    hwXQoSChipBufferOverrunAlarmObjects OBJECT IDENTIFIER ::= { hwXQoSObjects 138 }
    hwXQoSChipBufferOverrunAlarmTable OBJECT-TYPE
        SYNTAX SEQUENCE OF HwXQoSChipBufferOverrunAlarmEntry
        MAX-ACCESS not-accessible
        STATUS current
        DESCRIPTION
            "hwXQoSChipBufferOverrunAlarmTable"
        ::= { hwXQoSChipBufferOverrunAlarmObjects 1 }
    hwXQoSChipBufferOverrunAlarmEntry OBJECT-TYPE
        SYNTAX HwXQoSChipBufferOverrunAlarmEntry
        MAX-ACCESS not-accessible
        STATUS current
        DESCRIPTION
            "hwXQoSChipBufferOverrunEntry"
        INDEX { hwXQoSChipBufferOverrunAlarmSlotId, hwXQoSChipBufferOverrunAlarmChipId }
        ::= { hwXQoSChipBufferOverrunAlarmTable 1 }
    HwXQoSChipBufferOverrunAlarmEntry ::=
        SEQUENCE {
            hwXQoSChipBufferOverrunAlarmSlotId
                OCTET STRING,
            hwXQoSChipBufferOverrunAlarmChipId
                Integer32,
            hwXQoSChipBufferOverrunAlarmUsedLength
                Integer32,
            hwXQoSChipBufferOverrunAlarmThreshold
                Integer32
                }
    hwXQoSChipBufferOverrunAlarmSlotId OBJECT-TYPE
        SYNTAX OCTET STRING (SIZE (1..128))
        MAX-ACCESS read-only
        STATUS current
        DESCRIPTION
            "Slot ID."
        ::= { hwXQoSChipBufferOverrunAlarmEntry 1 }
    hwXQoSChipBufferOverrunAlarmChipId OBJECT-TYPE
        SYNTAX Integer32
        MAX-ACCESS read-only
        STATUS current
        DESCRIPTION
            "Chip ID."
        ::= { hwXQoSChipBufferOverrunAlarmEntry 2 }
    hwXQoSChipBufferOverrunAlarmUsedLength OBJECT-TYPE
        SYNTAX Integer32
        MAX-ACCESS read-only
        STATUS current
        DESCRIPTION
            "Used Length."
        ::= { hwXQoSChipBufferOverrunAlarmEntry 3 }
    hwXQoSChipBufferOverrunAlarmThreshold OBJECT-TYPE
        SYNTAX Integer32
        MAX-ACCESS read-only
        STATUS current
        DESCRIPTION
            "Threshold."
        ::= { hwXQoSChipBufferOverrunAlarmEntry 4 }
--END
--BEGIN
    hwXQoSPfcRxRateAlarmObjects OBJECT IDENTIFIER ::= { hwXQoSObjects 139 }
    
    hwXQoSPfcRxRateAlarmTable OBJECT-TYPE
        SYNTAX SEQUENCE OF HwXQoSPfcRxRateAlarmEntry
        MAX-ACCESS not-accessible
        STATUS current
        DESCRIPTION
        "hwXQoSPfcRxRateAlarmTable"
        ::= { hwXQoSPfcRxRateAlarmObjects 1 }
        
    hwXQoSPfcRxRateAlarmEntry OBJECT-TYPE
        SYNTAX HwXQoSPfcRxRateAlarmEntry
        MAX-ACCESS not-accessible
        STATUS current
        DESCRIPTION
        "hwXQoSPfcRxRateAlarmEntry"
        INDEX { hwXQoSPfcRxRateAlarmIfName, hwXQoSPfcRxRateAlarmPriority }
        ::= { hwXQoSPfcRxRateAlarmTable 1 }
        
    HwXQoSPfcRxRateAlarmEntry ::=
        SEQUENCE { 
            hwXQoSPfcRxRateAlarmIfName
                OCTET STRING,
            hwXQoSPfcRxRateAlarmPriority
                Integer32,
            hwXQoSPfcRxRateAlarmReceivedrate
                Integer32,
            hwXQoSPfcRxRateAlarmThreshold
                Integer32
                } 
        
    hwXQoSPfcRxRateAlarmIfName OBJECT-TYPE
        SYNTAX OCTET STRING
        MAX-ACCESS accessible-for-notify
        STATUS current
        DESCRIPTION
        "ifname."
        ::= { hwXQoSPfcRxRateAlarmEntry 1 } 
    hwXQoSPfcRxRateAlarmPriority OBJECT-TYPE
        SYNTAX Integer32
        MAX-ACCESS accessible-for-notify
        STATUS current
        DESCRIPTION
        "priority."
        ::= { hwXQoSPfcRxRateAlarmEntry 2 }
    hwXQoSPfcRxRateAlarmReceivedrate OBJECT-TYPE
        SYNTAX Integer32
        MAX-ACCESS accessible-for-notify
        STATUS current
        DESCRIPTION
        "detect number."
        ::= { hwXQoSPfcRxRateAlarmEntry 3 }
    hwXQoSPfcRxRateAlarmThreshold OBJECT-TYPE
        SYNTAX Integer32
        MAX-ACCESS accessible-for-notify
        STATUS current
        DESCRIPTION
        "threshold."
        ::= { hwXQoSPfcRxRateAlarmEntry 4 }

    hwXQoSPfcRxRateResumeObjects OBJECT IDENTIFIER ::= { hwXQoSObjects 140 }
    
    hwXQoSPfcRxRateResumeTable OBJECT-TYPE
        SYNTAX SEQUENCE OF HwXQoSPfcRxRateResumeEntry
        MAX-ACCESS not-accessible
        STATUS current
        DESCRIPTION
        "hwXQoSPfcRxRateResumeTable"
        ::= { hwXQoSPfcRxRateResumeObjects 1 }
        
    hwXQoSPfcRxRateResumeEntry OBJECT-TYPE
        SYNTAX HwXQoSPfcRxRateResumeEntry
        MAX-ACCESS not-accessible
        STATUS current
        DESCRIPTION
        "hwXQoSPfcRxRateResumeEntry"
        INDEX { hwXQoSPfcRxRateResumeIfName, hwXQoSPfcRxRateResumePriority }
        ::= { hwXQoSPfcRxRateResumeTable 1 }
        
    HwXQoSPfcRxRateResumeEntry ::=
        SEQUENCE { 
            hwXQoSPfcRxRateResumeIfName
                OCTET STRING,
            hwXQoSPfcRxRateResumePriority
                Integer32
                } 
        
    hwXQoSPfcRxRateResumeIfName OBJECT-TYPE
        SYNTAX OCTET STRING
        MAX-ACCESS accessible-for-notify
        STATUS current
        DESCRIPTION
        "ifname."
        ::= { hwXQoSPfcRxRateResumeEntry 1 } 
    hwXQoSPfcRxRateResumePriority OBJECT-TYPE
        SYNTAX Integer32
        MAX-ACCESS accessible-for-notify
        STATUS current
        DESCRIPTION
        "priority."
        ::= { hwXQoSPfcRxRateResumeEntry 2 }
--END
--BEGIN
    hwXQoSPfcTxRateAlarmObjects OBJECT IDENTIFIER ::= { hwXQoSObjects 141 }
    
    hwXQoSPfcTxRateAlarmTable OBJECT-TYPE
        SYNTAX SEQUENCE OF HwXQoSPfcTxRateAlarmEntry
        MAX-ACCESS not-accessible
        STATUS current
        DESCRIPTION
        "hwXQoSPfcTxRateAlarmTable"
        ::= { hwXQoSPfcTxRateAlarmObjects 1 }
        
    hwXQoSPfcTxRateAlarmEntry OBJECT-TYPE
        SYNTAX HwXQoSPfcTxRateAlarmEntry
        MAX-ACCESS not-accessible
        STATUS current
        DESCRIPTION
        "hwXQoSPfcTxRateAlarmEntry"
        INDEX { hwXQoSPfcTxRateAlarmIfName, hwXQoSPfcTxRateAlarmPriority }
        ::= { hwXQoSPfcTxRateAlarmTable 1 }
        
    HwXQoSPfcTxRateAlarmEntry ::=
        SEQUENCE { 
            hwXQoSPfcTxRateAlarmIfName
                OCTET STRING,
            hwXQoSPfcTxRateAlarmPriority
                Integer32,
            hwXQoSPfcTxRateAlarmTransmittedrate
                Integer32,
            hwXQoSPfcTxRateAlarmThreshold
                Integer32
                } 
        
    hwXQoSPfcTxRateAlarmIfName OBJECT-TYPE
        SYNTAX OCTET STRING
        MAX-ACCESS accessible-for-notify
        STATUS current
        DESCRIPTION
        "ifname."
        ::= { hwXQoSPfcTxRateAlarmEntry 1 } 
    hwXQoSPfcTxRateAlarmPriority OBJECT-TYPE
        SYNTAX Integer32
        MAX-ACCESS accessible-for-notify
        STATUS current
        DESCRIPTION
        "priority."
        ::= { hwXQoSPfcTxRateAlarmEntry 2 }
    hwXQoSPfcTxRateAlarmTransmittedrate OBJECT-TYPE
        SYNTAX Integer32
        MAX-ACCESS accessible-for-notify
        STATUS current
        DESCRIPTION
        "detect number."
        ::= { hwXQoSPfcTxRateAlarmEntry 3 }
    hwXQoSPfcTxRateAlarmThreshold OBJECT-TYPE
        SYNTAX Integer32
        MAX-ACCESS accessible-for-notify
        STATUS current
        DESCRIPTION
        "threshold."
        ::= { hwXQoSPfcTxRateAlarmEntry 4 }

    hwXQoSPfcTxRateResumeObjects OBJECT IDENTIFIER ::= { hwXQoSObjects 142 }
    
    hwXQoSPfcTxRateResumeTable OBJECT-TYPE
        SYNTAX SEQUENCE OF HwXQoSPfcTxRateResumeEntry
        MAX-ACCESS not-accessible
        STATUS current
        DESCRIPTION
        "hwXQoSPfcTxRateResumeTable"
        ::= { hwXQoSPfcTxRateResumeObjects 1 }
        
    hwXQoSPfcTxRateResumeEntry OBJECT-TYPE
        SYNTAX HwXQoSPfcTxRateResumeEntry
        MAX-ACCESS not-accessible
        STATUS current
        DESCRIPTION
        "hwXQoSPfcTxRateResumeEntry"
        INDEX { hwXQoSPfcTxRateResumeIfName, hwXQoSPfcTxRateResumePriority }
        ::= { hwXQoSPfcTxRateResumeTable 1 }
        
    HwXQoSPfcTxRateResumeEntry ::=
        SEQUENCE { 
            hwXQoSPfcTxRateResumeIfName
                OCTET STRING,
            hwXQoSPfcTxRateResumePriority
                Integer32
                } 
        
    hwXQoSPfcTxRateResumeIfName OBJECT-TYPE
        SYNTAX OCTET STRING
        MAX-ACCESS accessible-for-notify
        STATUS current
        DESCRIPTION
        "ifname."
        ::= { hwXQoSPfcTxRateResumeEntry 1 } 
    hwXQoSPfcTxRateResumePriority OBJECT-TYPE
        SYNTAX Integer32
        MAX-ACCESS accessible-for-notify
        STATUS current
        DESCRIPTION
        "priority."
        ::= { hwXQoSPfcTxRateResumeEntry 2 }
--END
--BEGIN
    hwXQosHeadRoomPoolApplyFailAlarmObjects OBJECT IDENTIFIER ::= { hwXQoSObjects 143 }
    
    hwXQosHeadRoomPoolApplyFailAlarmTable OBJECT-TYPE
        SYNTAX SEQUENCE OF HwXQosHeadRoomPoolApplyFailAlarmEntry
        MAX-ACCESS not-accessible
        STATUS current
        DESCRIPTION
        "hwXQosHeadRoomPoolApplyFailAlarmTable"
        ::= { hwXQosHeadRoomPoolApplyFailAlarmObjects 1 }
        
    hwXQosHeadRoomPoolApplyFailAlarmEntry OBJECT-TYPE
        SYNTAX HwXQosHeadRoomPoolApplyFailAlarmEntry
        MAX-ACCESS not-accessible
        STATUS current
        DESCRIPTION
        "hwXQosHeadRoomPoolApplyFailAlarmEntry"
        INDEX { hwXQosHeadRoomPoolApplyFailAlarmSlotId }
        ::= { hwXQosHeadRoomPoolApplyFailAlarmTable 1 }
        
    HwXQosHeadRoomPoolApplyFailAlarmEntry ::=
        SEQUENCE { 
            hwXQosHeadRoomPoolApplyFailAlarmSlotId
                OCTET STRING
                } 
        
    hwXQosHeadRoomPoolApplyFailAlarmSlotId OBJECT-TYPE
        SYNTAX OCTET STRING
        MAX-ACCESS accessible-for-notify
        STATUS current
        DESCRIPTION
        "Slot id."
        ::= { hwXQosHeadRoomPoolApplyFailAlarmEntry 1 }
--END
--BEGIN
    hwXQosHeadRoomPoolApplyFailAlarmResumeObjects OBJECT IDENTIFIER ::= { hwXQoSObjects 144 }
    
    hwXQosHeadRoomPoolApplyFailAlarmResumeTable OBJECT-TYPE
        SYNTAX SEQUENCE OF HwXQosHeadRoomPoolApplyFailAlarmResumeEntry
        MAX-ACCESS not-accessible
        STATUS current
        DESCRIPTION
        "hwXQosHeadRoomPoolApplyFailAlarmResumeTable"
        ::= { hwXQosHeadRoomPoolApplyFailAlarmResumeObjects 1 }
        
    hwXQosHeadRoomPoolApplyFailAlarmResumeEntry OBJECT-TYPE
        SYNTAX HwXQosHeadRoomPoolApplyFailAlarmResumeEntry
        MAX-ACCESS not-accessible
        STATUS current
        DESCRIPTION
        "hwXQosHeadRoomPoolApplyFailAlarmResumeEntry"
        INDEX { hwXQosHeadRoomPoolApplyFailAlarmResumeSlotId }
        ::= { hwXQosHeadRoomPoolApplyFailAlarmResumeTable 1 }
        
    HwXQosHeadRoomPoolApplyFailAlarmResumeEntry ::=
        SEQUENCE { 
            hwXQosHeadRoomPoolApplyFailAlarmResumeSlotId
                OCTET STRING
                } 
        
    hwXQosHeadRoomPoolApplyFailAlarmResumeSlotId OBJECT-TYPE
        SYNTAX OCTET STRING
        MAX-ACCESS accessible-for-notify
        STATUS current
        DESCRIPTION
        "Slot id."
        ::= { hwXQosHeadRoomPoolApplyFailAlarmResumeEntry 1 } 
--END
--BEGIN
    hwXQosPfcBufferApplyFailAlarmObjects OBJECT IDENTIFIER ::= { hwXQoSObjects 145 }
    
    hwXQosPfcBufferApplyFailAlarmTable OBJECT-TYPE
        SYNTAX SEQUENCE OF HwXQosPfcBufferApplyFailAlarmEntry
        MAX-ACCESS not-accessible
        STATUS current
        DESCRIPTION
        "hwXQosPfcBufferApplyFailAlarmTable"
        ::= { hwXQosPfcBufferApplyFailAlarmObjects 1 }
        
    hwXQosPfcBufferApplyFailAlarmEntry OBJECT-TYPE
        SYNTAX HwXQosPfcBufferApplyFailAlarmEntry
        MAX-ACCESS not-accessible
        STATUS current
        DESCRIPTION
        "hwXQosPfcBufferApplyFailAlarmEntry"
        INDEX { hwXQosPfcBufferApplyFailAlarmIfName, hwXQosPfcBufferApplyFailAlarmPriority, hwXQosPfcBufferApplyFailAlarmBufferType }
        ::= { hwXQosPfcBufferApplyFailAlarmTable 1 }
        
    HwXQosPfcBufferApplyFailAlarmEntry ::=
        SEQUENCE { 
            hwXQosPfcBufferApplyFailAlarmIfName
                OCTET STRING,
            hwXQosPfcBufferApplyFailAlarmPriority
                Integer32,
            hwXQosPfcBufferApplyFailAlarmBufferType
                OCTET STRING
                } 
        
    hwXQosPfcBufferApplyFailAlarmIfName OBJECT-TYPE
        SYNTAX OCTET STRING
        MAX-ACCESS accessible-for-notify
        STATUS current
        DESCRIPTION
        "Ifname."
        ::= { hwXQosPfcBufferApplyFailAlarmEntry 1 }
    hwXQosPfcBufferApplyFailAlarmPriority OBJECT-TYPE
        SYNTAX Integer32
        MAX-ACCESS accessible-for-notify
        STATUS current
        DESCRIPTION
        "Priority."
        ::= { hwXQosPfcBufferApplyFailAlarmEntry 2 }
    hwXQosPfcBufferApplyFailAlarmBufferType OBJECT-TYPE
        SYNTAX OCTET STRING
        MAX-ACCESS accessible-for-notify
        STATUS current
        DESCRIPTION
        "Priority."
        ::= { hwXQosPfcBufferApplyFailAlarmEntry 3 }
--END
--BEGIN
    hwXQosPfcBufferApplyFailAlarmResumeObjects OBJECT IDENTIFIER ::= { hwXQoSObjects 146 }
    
    hwXQosPfcBufferApplyFailAlarmResumeTable OBJECT-TYPE
        SYNTAX SEQUENCE OF HwXQosPfcBufferApplyFailAlarmResumeEntry
        MAX-ACCESS not-accessible
        STATUS current
        DESCRIPTION
        "hwXQosPfcBufferApplyFailAlarmResumeTable"
        ::= { hwXQosPfcBufferApplyFailAlarmResumeObjects 1 }
        
    hwXQosPfcBufferApplyFailAlarmResumeEntry OBJECT-TYPE
        SYNTAX HwXQosPfcBufferApplyFailAlarmResumeEntry
        MAX-ACCESS not-accessible
        STATUS current
        DESCRIPTION
        "hwXQosPfcBufferApplyFailAlarmResumeEntry"
        INDEX { hwXQosPfcBufferApplyFailAlarmResumeIfName, hwXQosPfcBufferApplyFailAlarmResumePriority, hwXQosPfcBufferApplyFailAlarmResumeBufferType }
        ::= { hwXQosPfcBufferApplyFailAlarmResumeTable 1 }
        
    HwXQosPfcBufferApplyFailAlarmResumeEntry ::=
        SEQUENCE { 
            hwXQosPfcBufferApplyFailAlarmResumeIfName
                OCTET STRING,
            hwXQosPfcBufferApplyFailAlarmResumePriority
                Integer32,
            hwXQosPfcBufferApplyFailAlarmResumeBufferType
                OCTET STRING
                } 
        
    hwXQosPfcBufferApplyFailAlarmResumeIfName OBJECT-TYPE
        SYNTAX OCTET STRING
        MAX-ACCESS accessible-for-notify
        STATUS current
        DESCRIPTION
        "Ifname."
        ::= { hwXQosPfcBufferApplyFailAlarmResumeEntry 1 }
    hwXQosPfcBufferApplyFailAlarmResumePriority OBJECT-TYPE
        SYNTAX Integer32
        MAX-ACCESS accessible-for-notify
        STATUS current
        DESCRIPTION
        "Priority."
        ::= { hwXQosPfcBufferApplyFailAlarmResumeEntry 2 }
    hwXQosPfcBufferApplyFailAlarmResumeBufferType OBJECT-TYPE
        SYNTAX OCTET STRING
        MAX-ACCESS accessible-for-notify
        STATUS current
        DESCRIPTION
        "Priority."
        ::= { hwXQosPfcBufferApplyFailAlarmResumeEntry 3 }
--END
--BEGIN
    hwXQoSFlowspecNotSupportBoardEventObjects OBJECT IDENTIFIER ::= { hwXQoSObjects 147 }

    hwXQoSFlowspecNotSupportBoardEventTable OBJECT-TYPE
        SYNTAX SEQUENCE OF HwXQoSFlowspecNotSupportBoardEventEntry
        MAX-ACCESS not-accessible
        STATUS current
        DESCRIPTION
            "hwXQoSFlowspecNotSupportBoardEventTable"
        ::= { hwXQoSFlowspecNotSupportBoardEventObjects 1 }

    hwXQoSFlowspecNotSupportBoardEventEntry OBJECT-TYPE
        SYNTAX HwXQoSFlowspecNotSupportBoardEventEntry
        MAX-ACCESS not-accessible
        STATUS current
        DESCRIPTION
            "hwXQoSFlowspecNotSupportBoardEventEntry"
        INDEX { hwXQoSFlowspecNotSupportBoardEventChassisID, hwXQoSFlowspecNotSupportBoardEventSlotID, hwXQoSFlowspecNotSupportBoardEventRuleType, hwXQoSFlowspecNotSupportBoardEventAddrType, hwXQoSFlowspecNotSupportBoardEventServiceType }
        ::= { hwXQoSFlowspecNotSupportBoardEventTable 1 }

    HwXQoSFlowspecNotSupportBoardEventEntry ::=
        SEQUENCE {
            hwXQoSFlowspecNotSupportBoardEventChassisID
                Unsigned32,
            hwXQoSFlowspecNotSupportBoardEventSlotID
                Unsigned32,
            hwXQoSFlowspecNotSupportBoardEventRuleType
                OCTET STRING,
            hwXQoSFlowspecNotSupportBoardEventAddrType
                OCTET STRING,
            hwXQoSFlowspecNotSupportBoardEventServiceType
                OCTET STRING
        }

    hwXQoSFlowspecNotSupportBoardEventChassisID OBJECT-TYPE
        SYNTAX Unsigned32
        MAX-ACCESS accessible-for-notify
        STATUS current
        DESCRIPTION
            "Chassis ID."
        ::= { hwXQoSFlowspecNotSupportBoardEventEntry 1 }

    hwXQoSFlowspecNotSupportBoardEventSlotID OBJECT-TYPE
        SYNTAX Unsigned32
        MAX-ACCESS accessible-for-notify
        STATUS current
        DESCRIPTION
            "Slot ID."
        ::= { hwXQoSFlowspecNotSupportBoardEventEntry 2 }

    hwXQoSFlowspecNotSupportBoardEventRuleType OBJECT-TYPE
        SYNTAX OCTET STRING (SIZE (1..63))
        MAX-ACCESS accessible-for-notify
        STATUS current
        DESCRIPTION
            "Rule type."
        ::= { hwXQoSFlowspecNotSupportBoardEventEntry 3 }

    hwXQoSFlowspecNotSupportBoardEventAddrType OBJECT-TYPE
        SYNTAX OCTET STRING (SIZE (1..63))
        MAX-ACCESS accessible-for-notify
        STATUS current
        DESCRIPTION
            "Address family type."
        ::= { hwXQoSFlowspecNotSupportBoardEventEntry 4 }

    hwXQoSFlowspecNotSupportBoardEventServiceType OBJECT-TYPE
        SYNTAX OCTET STRING (SIZE (1..63))
        MAX-ACCESS accessible-for-notify
        STATUS current
        DESCRIPTION
            "Service type."
        ::= { hwXQoSFlowspecNotSupportBoardEventEntry 5 }
--END
--BEGIN
    hwXAclEpgGroupMemberMacAlarmObjects OBJECT IDENTIFIER ::= { hwXQoSObjects 148 }

    hwXAclEpgGroupMemberMacAlarmMacAddress OBJECT-TYPE
        SYNTAX OCTET STRING
        MAX-ACCESS accessible-for-notify
        STATUS current
        DESCRIPTION
            "mac address."
        ::= { hwXAclEpgGroupMemberMacAlarmObjects 1 }
    hwXAclEpgGroupMemberMacAlarmVlanId OBJECT-TYPE
        SYNTAX OCTET STRING
        MAX-ACCESS accessible-for-notify
        STATUS current
        DESCRIPTION
            "vlan id."
        ::= { hwXAclEpgGroupMemberMacAlarmObjects 2 }
    hwXAclEpgGroupMemberMacAlarmBdId OBJECT-TYPE
        SYNTAX OCTET STRING
        MAX-ACCESS accessible-for-notify
        STATUS current
        DESCRIPTION
            "bridge-domain id."
        ::= { hwXAclEpgGroupMemberMacAlarmObjects 3 }
    hwXAclEpgGroupMemberMacAlarmSegmentId OBJECT-TYPE
        SYNTAX OCTET STRING
        MAX-ACCESS accessible-for-notify
        STATUS current
        DESCRIPTION
            "segment id."
        ::= { hwXAclEpgGroupMemberMacAlarmObjects 4 }
    hwXAclEpgGroupMemberMacAlarmSlotid OBJECT-TYPE
        SYNTAX OCTET STRING
        MAX-ACCESS accessible-for-notify
        STATUS current
        DESCRIPTION
            "slot id."
        ::= { hwXAclEpgGroupMemberMacAlarmObjects 5 }
--END
--BEGIN
    hwXQoSBgpFlowspecDestinationCommunityOverAlarmObjects OBJECT IDENTIFIER ::= { hwXQoSObjects 149 }

    hwXQoSBgpFlowspecDestinationCommunityOverAlarmTable OBJECT-TYPE
        SYNTAX SEQUENCE OF HwXQoSBgpFlowspecDestinationCommunityOverAlarmEntry
        MAX-ACCESS not-accessible
        STATUS current
        DESCRIPTION
            "hwXQoSBgpFlowspecDestinationCommunityOverAlarmTable"
        ::= { hwXQoSBgpFlowspecDestinationCommunityOverAlarmObjects 1 }

    hwXQoSBgpFlowspecDestinationCommunityOverAlarmEntry OBJECT-TYPE
        SYNTAX HwXQoSBgpFlowspecDestinationCommunityOverAlarmEntry
        MAX-ACCESS not-accessible
        STATUS current
        DESCRIPTION
            "hwXQoSBgpFlowspecDestinationCommunityOverAlarmEntry"
        INDEX { hwXQoSBgpFlowspecDestinationCommunityOverAlarmAddrFamily }
        ::= { hwXQoSBgpFlowspecDestinationCommunityOverAlarmTable 1 }

    HwXQoSBgpFlowspecDestinationCommunityOverAlarmEntry ::=
        SEQUENCE {
            hwXQoSBgpFlowspecDestinationCommunityOverAlarmAddrFamily
                OCTET STRING
        }

    hwXQoSBgpFlowspecDestinationCommunityOverAlarmAddrFamily OBJECT-TYPE
        SYNTAX OCTET STRING (SIZE (1..63))
        MAX-ACCESS accessible-for-notify
        STATUS current
        DESCRIPTION
            "Address family type."
        ::= { hwXQoSBgpFlowspecDestinationCommunityOverAlarmEntry 1 }
--END
--BEGIN
    hwXQoSTrafficPolicyRuleResoucePreAlarmObjects OBJECT IDENTIFIER ::= { hwXQoSObjects 150 }

    hwXQoSTrafficPolicyRuleResoucePreAlarmTable OBJECT-TYPE
        SYNTAX SEQUENCE OF HwXQoSTrafficPolicyRuleResoucePreAlarmEntry
        MAX-ACCESS not-accessible
        STATUS current
        DESCRIPTION
            "hwXQoSTrafficPolicyRuleResoucePreAlarmTable"
        ::= { hwXQoSTrafficPolicyRuleResoucePreAlarmObjects 1 }

    hwXQoSTrafficPolicyRuleResoucePreAlarmEntry OBJECT-TYPE
        SYNTAX HwXQoSTrafficPolicyRuleResoucePreAlarmEntry
        MAX-ACCESS not-accessible
        STATUS current
        DESCRIPTION
            "hwXQoSTrafficPolicyRuleResoucePreAlarmEntry"
        INDEX { hwXQoSTrafficPolicyRuleResoucePreAlarmSlotId, hwXQoSTrafficPolicyRuleResoucePreAlarmThreshold, hwXQoSTrafficPolicyRuleResoucePreAlarmReasonId }
        ::= { hwXQoSTrafficPolicyRuleResoucePreAlarmTable 1 }

    HwXQoSTrafficPolicyRuleResoucePreAlarmEntry ::=
        SEQUENCE {
            hwXQoSTrafficPolicyRuleResoucePreAlarmSlotId
                OCTET STRING,
            hwXQoSTrafficPolicyRuleResoucePreAlarmThreshold
                Unsigned32,
            hwXQoSTrafficPolicyRuleResoucePreAlarmReasonId
                Integer32,
            hwXQoSTrafficPolicyRuleResoucePreAlarmReasonDescription
                OCTET STRING
        }

    hwXQoSTrafficPolicyRuleResoucePreAlarmSlotId OBJECT-TYPE
        SYNTAX OCTET STRING (SIZE (1..31))
        MAX-ACCESS accessible-for-notify
        STATUS current
        DESCRIPTION
            "The ID of slot."
        ::= { hwXQoSTrafficPolicyRuleResoucePreAlarmEntry 1 }

    hwXQoSTrafficPolicyRuleResoucePreAlarmThreshold OBJECT-TYPE
        SYNTAX Unsigned32
        MAX-ACCESS accessible-for-notify
        STATUS current
        DESCRIPTION
            "The threshold of alarm."
        ::= { hwXQoSTrafficPolicyRuleResoucePreAlarmEntry 2 }

    hwXQoSTrafficPolicyRuleResoucePreAlarmReasonId OBJECT-TYPE
        SYNTAX Integer32
        MAX-ACCESS accessible-for-notify
        STATUS current
        DESCRIPTION
            "The ID of alarm reason."
        ::= { hwXQoSTrafficPolicyRuleResoucePreAlarmEntry 3 }

    hwXQoSTrafficPolicyRuleResoucePreAlarmReasonDescription OBJECT-TYPE
        SYNTAX OCTET STRING (SIZE (1..511))
        MAX-ACCESS accessible-for-notify
        STATUS current
        DESCRIPTION
            "The description of the alarm cause."
        ::= { hwXQoSTrafficPolicyRuleResoucePreAlarmEntry 4 }
--END

    hwXQoSFLowMatrixRailInvalidAlarmObjects OBJECT IDENTIFIER ::= { hwXQoSObjects 151}
    
   hwXQoSFLowMatrixRailInvalidAlarmTable OBJECT-TYPE
        SYNTAX SEQUENCE OF HwXQoSFLowMatrixRailInvalidAlarmEntry
        MAX-ACCESS not-accessible
        STATUS current
        DESCRIPTION
        "hwXQoSFLowMatrixRailInvalidAlarmTable"
        ::= { hwXQoSFLowMatrixRailInvalidAlarmObjects 1 }
        
    hwXQoSFLowMatrixRailInvalidAlarmEntry OBJECT-TYPE
        SYNTAX HwXQoSFLowMatrixRailInvalidAlarmEntry
        MAX-ACCESS not-accessible
        STATUS current
        DESCRIPTION
        "hwXQoSFLowMatrixRailInvalidAlarmEntry"
        INDEX { hwXQoSFLowMatrixRailSlotId, hwXQoSFLowMatrixRailSourceIp, hwXQoSFLowMatrixRailDestinationIp }
        ::= { hwXQoSFLowMatrixRailInvalidAlarmTable 1 }
        
    HwXQoSFLowMatrixRailInvalidAlarmEntry ::=
        SEQUENCE {
            hwXQoSFLowMatrixRailSlotId
                OCTET STRING,
            hwXQoSFLowMatrixRailSourceIp
                IpAddress,
            hwXQoSFLowMatrixRailDestinationIp
                IpAddress,
            hwXQoSFLowMatrixRailOutPort
                OCTET STRING
                } 
    hwXQoSFLowMatrixRailSlotId OBJECT-TYPE
        SYNTAX OCTET STRING (SIZE (1..31))
        MAX-ACCESS accessible-for-notify
        STATUS current
        DESCRIPTION
            "The ID of slot."
        ::= { hwXQoSFLowMatrixRailInvalidAlarmEntry 1 }

    hwXQoSFLowMatrixRailSourceIp OBJECT-TYPE
        SYNTAX IpAddress
        MAX-ACCESS accessible-for-notify
        STATUS current
        DESCRIPTION
        "Source IP address."
        ::= { hwXQoSFLowMatrixRailInvalidAlarmEntry 2 } 

    hwXQoSFLowMatrixRailDestinationIp OBJECT-TYPE
        SYNTAX IpAddress
        MAX-ACCESS accessible-for-notify
        STATUS current
        DESCRIPTION
        "Destination IP address."
        ::= { hwXQoSFLowMatrixRailInvalidAlarmEntry 3 } 

    hwXQoSFLowMatrixRailOutPort OBJECT-TYPE
        SYNTAX OCTET STRING
        MAX-ACCESS accessible-for-notify
        STATUS current
        DESCRIPTION
        "Out port."
        ::= { hwXQoSFLowMatrixRailInvalidAlarmEntry 4 } 

--BEGIN
    hwXQoSBgpFlowspecDDoSLowPriorityAlarmObjects OBJECT IDENTIFIER ::= { hwXQoSObjects 152 }

    hwXQoSBgpFlowspecDDoSLowPriorityAlarmTable OBJECT-TYPE
        SYNTAX SEQUENCE OF HwXQoSBgpFlowspecDDoSLowPriorityAlarmEntry
        MAX-ACCESS not-accessible
        STATUS current
        DESCRIPTION
            "hwXQoSBgpFlowspecDDoSLowPriorityAlarmTable"
        ::= { hwXQoSBgpFlowspecDDoSLowPriorityAlarmObjects 1 }

    hwXQoSBgpFlowspecDDoSLowPriorityAlarmEntry OBJECT-TYPE
        SYNTAX HwXQoSBgpFlowspecDDoSLowPriorityAlarmEntry
        MAX-ACCESS not-accessible
        STATUS current
        DESCRIPTION
            "hwXQoSBgpFlowspecDDoSLowPriorityAlarmEntry"
        INDEX { hwXQoSBgpFlowspecDDoSLowPriorityAlarmSlotId, hwXQoSBgpFlowspecDDoSLowPriorityAlarmReasonId }
        ::= { hwXQoSBgpFlowspecDDoSLowPriorityAlarmTable 1 }

    HwXQoSBgpFlowspecDDoSLowPriorityAlarmEntry ::=
        SEQUENCE {
            hwXQoSBgpFlowspecDDoSLowPriorityAlarmSlotId
                OCTET STRING,
            hwXQoSBgpFlowspecDDoSLowPriorityAlarmReasonId
                Integer32
        }

    hwXQoSBgpFlowspecDDoSLowPriorityAlarmSlotId OBJECT-TYPE
        SYNTAX OCTET STRING (SIZE (1..31))
        MAX-ACCESS accessible-for-notify
        STATUS current
        DESCRIPTION
            "The ID of slot."
        ::= { hwXQoSBgpFlowspecDDoSLowPriorityAlarmEntry 1 }

    hwXQoSBgpFlowspecDDoSLowPriorityAlarmReasonId OBJECT-TYPE
        SYNTAX Integer32
        MAX-ACCESS accessible-for-notify
        STATUS current
        DESCRIPTION
            "The ID of alarm reason."
        ::= { hwXQoSBgpFlowspecDDoSLowPriorityAlarmEntry 2 }
--END

--BEGIN
    hwXACLEPGAlarmObjects OBJECT IDENTIFIER ::= { hwXQoSObjects 153 }

    hwXACLEPGAlarmSlotid OBJECT-TYPE
        SYNTAX OCTET STRING
        MAX-ACCESS accessible-for-notify
        STATUS current
        DESCRIPTION
            "Slot ID."
        ::= { hwXACLEPGAlarmObjects 1 }
    hwXACLEPGAlarmView OBJECT-TYPE
        SYNTAX OCTET STRING
        MAX-ACCESS accessible-for-notify
        STATUS current
        DESCRIPTION
            "View."
        ::= { hwXACLEPGAlarmObjects 2 }
    hwXACLEPGAlarmPolicy OBJECT-TYPE
        SYNTAX OCTET STRING
        MAX-ACCESS accessible-for-notify
        STATUS current
        DESCRIPTION
            "Policy name."
        ::= { hwXACLEPGAlarmObjects 3 }
    hwXACLEPGAlarmRouteTemplate OBJECT-TYPE
        SYNTAX OCTET STRING
        MAX-ACCESS accessible-for-notify
        STATUS current
        DESCRIPTION
            "Route template name."
        ::= { hwXACLEPGAlarmObjects 4 }
--END

    END

--
-- HUAWEI-XQoS-MIB.mib
--
