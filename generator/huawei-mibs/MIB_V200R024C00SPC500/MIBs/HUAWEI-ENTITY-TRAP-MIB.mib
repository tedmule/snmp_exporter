-- ============================================================================
-- Copyright (C) 2024 by  HUAWEI TECHNOLOGIES. All rights reserved.
-- Description: 
-- Reference: None
-- Version: V5.02
-- ============================================================================

	HUAWEI-ENTITY-TRAP-MIB DEFINITIONS ::= BEGIN
 
		IMPORTS
			hwEntityOperStatus
				FROM HUAWEI-ENTITY-EXTENT-MIB
			ifOperStatus,ifAdminStatus
				FROM RFC1213-MIB	
			entPhysicalIndex, entPhysicalName,entPhysicalContainedIn			
				FROM ENTITY-MIB			
			hwBaseTrapSeverity, hwBaseTrapProbableCause, hwBaseTrapEventType,hwBaseTrapReasonDescr			
				FROM HUAWEI-BASE-TRAP-MIB						
			ifIndex, ifName			
				FROM IF-MIB			
			hwDatacomm			
				FROM HUAWEI-MIB			
			IANAItuProbableCause			
				FROM IANA-ITU-ALARM-TC-MIB			
			OBJECT-GROUP, MODULE-COMPLIANCE, NOTIFICATION-GROUP			
				FROM SNMPv2-CONF		
             			TEXTUAL-CONVENTION, MacAddress
                                                                                     FROM SNMPv2-TC			
			Integer32, OBJECT-TYPE, MODULE-IDENTITY, NOTIFICATION-TYPE			
				FROM SNMPv2-SMI
			hwGtlItemIndex, hwGtlItemName
				FROM HUAWEI-GTL-MIB;
	
	
--   January 17, 2007 at 00:00 GMT
-- 1.3.6.1.4.1.2011.5.25.219
-- January 17, 2007 at 00:00 GMT
		-- 1.3.6.1.4.1.2011.5.25.219
		hwEntityTrapMIB MODULE-IDENTITY 
			LAST-UPDATED "202409181700Z"
			ORGANIZATION 
				"Huawei Technologies Co.,Ltd."		
			CONTACT-INFO 
				"Huawei Industrial Base
				  Bantian, Longgang
				   Shenzhen 518129
				   People's Republic of China
				   Website: http://www.huawei.com
				   Email: support@huawei.com
				 "
DESCRIPTION 
 				"This is the base trap definition for DataCom."
         
         REVISION     "202409181700Z"
         DESCRIPTION  "v5.02 Adapts to the error code indicating that the subcard is powered off due to insufficient power supply."
	 
		 REVISION     "202409102131Z"
         DESCRIPTION  "v5.01 Add hwDeviceRebootTrap"

		 REVISION     "202409061749Z"
         DESCRIPTION  "v4.40 modify the hwBandwidthOfAllBoardsExceedsThresholdAlarm hwBandwidthOfAllBoardsExceedsThresholdAlarmResume."

         REVISION     "202409041749Z"
         DESCRIPTION  "v4.39 add hwFwdPacketLoss."

         REVISION     "202407271120Z"
         DESCRIPTION  "v4.38 change MAX-ACCESS of hwHelpinfo to accessible-for-notify."

         REVISION     "202407191450Z"
         DESCRIPTION  "v4.37 modify the liquid alarm name."

         REVISION     "202407112233Z"
         DESCRIPTION  "v4.36 add hwValveInspectFault hwChannelFault ."

         REVISION     "202407031744Z"
         DESCRIPTION  "v4.35 modify hwOpticalInvalid  hwOpticalInvalid 136263 136264 136265."

         REVISION     "202406272028Z"
         DESCRIPTION  "v4.34 add hwForwardEngineModelFail  hwForwardEnginePortFail 155907,155909,155909,155910,155911,155912,155913.155914."

         REVISION     "202406061030Z"
         DESCRIPTION  "v4.33 delete 136258 and fix order 135951,136246,136247,136248,136249,136254,136256,136257,136259,136260,136261,136262."

         REVISION     "202406041930Z"
         DESCRIPTION  "v4.32 add hwBoardFail 136256,136257,136258,136259,136260,136261,136262,136247,136248,136249,136246,136254,135951."

         REVISION     "202406041530Z"
         DESCRIPTION  "v4.31 add hwBoardFail 132383."

         REVISION     "202404301130Z"
         DESCRIPTION  "v4.30 add hwBoardFail 132385, 132386."

         REVISION     "202404301130Z"
         DESCRIPTION  "v4.29 add hwBoardFail 132382."

         REVISION     "202404281100Z"
         DESCRIPTION  "v4.28 add hwOpticalInvalid 136255."

         REVISION     "202404031700Z"
         DESCRIPTION  "v4.27 add hwAvaMemInsufficient, hwAvaMemInsufficientResume, hwAvailableMemory, hwAvailableMemoryThreshold."

         REVISION     "202403291520Z"
         DESCRIPTION  "v4.26 Add hwChassisPowerChanged."

		 REVISION     "202403291500Z"
         DESCRIPTION  "v4.25 add hwBandwidthOfAllBoardsExceedsThresholdAlarm, hwBandwidthOfAllBoardsExceedsThresholdAlarmResume."
		 
	 REVISION     "202403231500Z"
         DESCRIPTION  "v4.24 add hwValveTrap."

         REVISION     "202403111500Z"
         DESCRIPTION  "v3.99 add hwEsnMismatch, hwMacNumMismatch."

         REVISION     "202403041038Z"
         DESCRIPTION  "v4.22 Add hwEntityTrapEntType board(7) and other(255)"

         REVISION     "202402051400Z"
         DESCRIPTION  "v4.21 Add hwForwardEngineFail 155906"
		 
         REVISION     "202310251612Z"
         DESCRIPTION  "v4.19 Add hwChassisFail 131367 and hwOpticalFail 135950"

         REVISION     "202308291600Z"
         DESCRIPTION  "v4.18 Modify hwBoardFail."

         REVISION     "202308281600Z"
         DESCRIPTION  "v4.18 Add hwBoardFail, 132357."

         REVISION     "202308221644Z"
         DESCRIPTION  "v4.17 Modify hwTmStatusChangeAlarm hwTmStatusChangeAlarmResume."

         REVISION     "202308211435Z"
         DESCRIPTION  "v4.16 Add hwBoardFail 132372."

         REVISION     "202308021501Z"
         DESCRIPTION  "v4.15 Add theSystemMemoryOverload and theNandOfChipWasFaulty."

	 REVISION     "202307211614Z"
         DESCRIPTION  "v4.14 Modify hwBoardUpCoverStackAlarm hwBoardUpCoverStackResume."

         REVISION     "202307141443Z"
         DESCRIPTION  "v4.13 Modify hwTmStatusChangeAlarm hwTmStatusChangeAlarmResume."

         REVISION     "202307031620Z"
         DESCRIPTION  "v4.12 Add hwTmStatusChangeAlarm hwTmStatusChangeAlarmResume."

         REVISION     "202306201920Z"
         DESCRIPTION  "v4.11 Modify hwChassisMinorAlarm hwChassisMinorAlarmResume."

         REVISION     "202306101525Z"
         DESCRIPTION  "v4.10 Change thePowerSupplyModuleMismatchesInTheFrame to thePowerSupplyModuleMismatch."

         REVISION     "202306081050Z"
         DESCRIPTION  "v4.09 Add hwEntityFileSystemAbnormal 152065, 152066, 152070."

         REVISION     "202305271026Z"
         DESCRIPTION  "v4.08 Add hwChassisMinorAlarm, hwChassisMinorAlarmResume, hwSlicePowerFail, hwWarmBackFail"

         REVISION     "202305241026Z"
         DESCRIPTION  "v4.07 Add hwBoardFail 132369"

         REVISION     "202304181421Z"
         DESCRIPTION  "v4.06 Modify hwStorageInsufficient, add hwEntityThresholdTip"

         REVISION     "202303302106Z"
         DESCRIPTION  "v4.05 Change datatype of hwLpuSlotId to STRING"

         REVISION     "202303161721Z"
         DESCRIPTION  "v4.04 Add hwChassisFail 138253."

         REVISION     "202303131721Z"
         DESCRIPTION  "v4.03 Add hwChassisFail 131361."

         REVISION     "202303111721Z"
         DESCRIPTION  "v4.02 Add hwChassisFail 131360."

         REVISION     "202302181900Z"
         DESCRIPTION  "v4.01 Add hwBoardFail 132221."

         REVISION     "202302150900Z"
         DESCRIPTION  "v4.00 Add hwBoardFail 132272, 132300."

         REVISION     "202301281600Z"
         DESCRIPTION  "v3.99 Add hwBoardInvalid 132721."

         REVISION     "202212021600Z"
         DESCRIPTION  "v3.98 Add hwBoardFail 132325."

         REVISION     "202212021600Z"
         DESCRIPTION  "v3.96 Modify the description of 157955."

         REVISION     "202211291600Z"
         DESCRIPTION  "v3.96 Add hwPortFail, 157952, 157953, 157954, 157955."

         REVISION     "202211041608Z"
         DESCRIPTION  "v3.95 Modify  hwBoardFail, 132348, 132349,
         Add hwBoardFail, hwBoardInvalid, hwBoardWarning, 132202, 132214, 132293, 132298, 132323, 132332, 132333, 132334,132335, 132352, 132353, 132354, 132674, 132678, 132695, 132696, 132712, 132713, 132714, 147218,
         Roll back reason code 132213, 132690 and 132691 to v3.92"

         REVISION     "202211031624Z"
         DESCRIPTION  "v3.94 add hwBoardFail, hwBoardWarning, 132212, 147221,
         Modify hwBoardFail, theFullinSignalOfTheBoardIsAbnormal, theFullinSignalOfTheBoardIsAbnormal"

         REVISION     "202210282030Z"
         DESCRIPTION  "v3.93 add hwBoardFail, hwBoardInvalid, hwBoardWarning, 132207, 132208, 132209, 132215, 132216, 132279, 132285, 132286, 132287, 132296, 132297, 132313, 132314, 132319, 132320, 132321, 132324, 132685, 132686, 147217,
         Modify hwBoardFail, hwBoardInvalid, hwCardFail, 132213, 132690, 132691, 135204"

         REVISION     "202210191830Z"
         DESCRIPTION  "v3.92 add theMasterAndSlaveCFCARDsSizeDismatch"

         REVISION     "202209271528Z"
         DESCRIPTION  "v3.91 add hwBoardFail, hwBoardFailResume, 132347, 132348, 132349."

         REVISION     "202208041138Z"
         DESCRIPTION  "v3.90 add  trap node hwEntityFileSystemAbnormalResume."
REVISION     "202207091000Z"
         DESCRIPTION  "v3.89 add  hwCardBandwidthModeChange OBJECTS ."

         REVISION     "202207021150Z"
         DESCRIPTION  "v3.88 add  BoardBurntDueToHighPoEPower."

         REVISION     "202203251150Z"
         DESCRIPTION  "v3.87 add  hwSystemTrap, hwSystemBakeupStartup."

         REVISION     "202203091000Z"
         DESCRIPTION  "v3.86 add  hwCrlInvalid, hwCrlInvalidResume."

         REVISION     "202202261000Z"
         DESCRIPTION  "v3.85 modify hwPortFail, hwPortFailResume."

         REVISION     "202202151000Z"
         DESCRIPTION  "v3.84 add hwPortFail, hwPortFailResume, 132330, 132331."
         
         REVISION     "202112301000Z"
         DESCRIPTION  "v3.83 add hwSACSessionOverloadTrap hwSACSessionOverloadRestoreTrap hwCapCurSACSessionRate hwCapUpperSACSessionThreshold hwCapLowerSACSessionThreshold."

         REVISION     "202112131000Z"
         DESCRIPTION  "v3.82 add hwPeerDevPnPTrunkAggregationFailure."

         REVISION     "202111201000Z"
         DESCRIPTION  "v3.81 add thePowerCurrentOfTheOpticalModuleIsTooHigh."

         REVISION     "202111131000Z"
         DESCRIPTION  "v3.80 modify hwFrerLinkPacketLossTrap."

         REVISION     "202111121000Z"
         DESCRIPTION  "v3.79 modify hwFrerLinkPacketLossTrap."

	 REVISION     "202109281000Z"
         DESCRIPTION  "v3.78 add hwCapTableUsageTrap hwSipfpmFlowOverloadTrap hwSipfpmFlowOverloadRestoreTrap hwCapCurSipfpmFlowRate hwCapUpperSipfpmFlowThreshold hwCapLowerSipfpmFlowThreshold"

         REVISION     "202109161000Z"
         DESCRIPTION  "v3.77 add 136996,132315,132316,132317,132318."

         REVISION     "202109042200Z"
         DESCRIPTION  "v3.76 add OBJECTS to hwInsSpaceLackTrap and hwVfpSysCheckErrResume."
				
         REVISION     "202108282200Z"
         DESCRIPTION  "v3.75 add hwFrerLinkPacketLossTrap."
			
         REVISION     "202107142200Z"
         DESCRIPTION  "v3.74 add 143627."
	
         REVISION     "202106032200Z"
         DESCRIPTION  "v3.73 add hwNoConsolePassword."

         REVISION     "202105250000Z"
         DESCRIPTION  "v3.72, Add trap node hwVirtualLicenseNearDeadlineResume ."

		 REVISION     "202103161030Z"
         DESCRIPTION  "v3.71 add hwPowerLimited."

		 REVISION     "202102270955Z"
         DESCRIPTION  "V3.70, add the objects of hwCapSingleCoreThresholdCurrent, hwCapSingleCoreIndex, hwCapSingleCoreThresholdValue, hwCapMemType, hwCapMemThresholdValue, hwCapMemThresholdCurrent and the traps of hwCapMemUtilizationResume, hwCapMemUtilizationRising,hwCapSingleCoreCPUUtilizationRising,hwCapSingleCoreCPUUtilizationResume ."

         REVISION     "202102092131Z"
         DESCRIPTION  "v3.69 add  hwContainerName."
         
		 REVISION     "202102022131Z"
         DESCRIPTION  "v3.68 add hwCertExpired hwCertExpiredResume."
		 
		 REVISION     "202101301644Z"
         DESCRIPTION  "v3.67 add hwCfgDatabaseException."
				
         REVISION     "202101291600Z"
         DESCRIPTION  "v3.66 add hwNetconfDatabaseAbnormal hwNetconfDatabaseRestore."
		 
         REVISION     "202101231110Z"
         DESCRIPTION  "v3.65 add 135204."

		 REVISION     "202101161500Z"
		 DESCRIPTION  "v3.64 add hwContainerCpuUtilizationRising hwContainerCpuUtilizationResume hwContainerMemUtilizationRising hwContainerMemUtilizationResume hwContainerStorageInsufficient hwContainerStorageInsufficientResume hwContainerAbnormal hwContainerAbnormalResume hwContainerAppAbnormal hwContainerAppAbnormalResume"
		 
		 REVISION     "202012301500Z"
		 DESCRIPTION  "v3.63 add hwFwdCPUUtilizationRising, hwFwdCPUUtilizationResume"
		 
         REVISION     "202012211500Z"
         DESCRIPTION  "v3.62 add 132425,132426,132427,132428,132429,132690,132691,132692,132693,132694."

         REVISION     "202012101500Z"
         DESCRIPTION  "v3.61 add 132290,132699,132302."

         REVISION     "202012071605Z"
         DESCRIPTION  "v3.60 Modify hwInnerPortSlotId."

         REVISION     "202012051531Z"
         DESCRIPTION  "v3.59 add hwBatteryGroupFault, hwBatteryGroupFaultResume, hwBatteryFault, hwBatteryFaultResume, hwBatteryMinorFault, hwBatteryMinorFaultResume."	

         REVISION     "202011181531Z"
         DESCRIPTION  "v3.58 add TheForwardingPipeIsFaulty."
         
         REVISION     "202011060819Z"
         DESCRIPTION  "v3.57 add hwInternalProtocolNetworkPortFaultAlarm, hwInternalProtocolNetworkPortFaultResume."

         REVISION     "202010301150Z"
         DESCRIPTION  "v3.56 add 135681."
         REVISION     "202010161646Z"
         DESCRIPTION  "v3.55 add 132303."

         REVISION     "202009092040Z"
         DESCRIPTION  "v3.54 add 136222, 143624, 75315, 132143, 132132, 136223, 136233,136234."

         REVISION     "202008170000Z"
         DESCRIPTION  "v3.53 Modify hwSoftwareVersion, hwStartupSoftwareFileName, hwSystemRollback." 

         REVISION     "202008120000Z"
         DESCRIPTION  "v3.52 add hwBoardLicenseActSuccess, hwBoardLicenseActFail." 

         REVISION     "202007281736Z"
         DESCRIPTION  "v3.51 Modify trap node hwVfpSysCheckErr hwVfpSysCheckErrResume."

         REVISION     "202007271736Z"
         DESCRIPTION  "v3.50 Modify trap node hwChassisFail."

         REVISION     "202007221734Z"
         DESCRIPTION  "v3.49 Modify trap node hwOpticalUnAuthorized."

         REVISION     "202006161732Z"
         DESCRIPTION  "v3.48 add hwStorageInsufficient, hwStorageInsufficientResume." 

         REVISION     "202006121940Z"
         DESCRIPTION  "v3.47 add hwInnerPortPacketCrcErr,  hwInnerPortPacketCrcErrResume, hwInnerPortLinkDown, hwInnerPortLinkUp." 

         REVISION     "202006121118Z"
         DESCRIPTION  "v3.46 Modify trap node hwForwardEngineInvalid."

         REVISION     "202006051123Z"
         DESCRIPTION  "v3.45 Modify trap node hwForwardEngineInvalid." 

         REVISION     "202004241500Z"
         DESCRIPTION  "v3.44 Modify trap node hwAllLpuSfuFailResume." 

         REVISION     "202004022100Z"
         DESCRIPTION  "v3.43 add hwForwardEngineFail,  hwForwardEngineFailResume, hwForwardEngineInvalid, hwForwardEngineInvalidResume." 

         REVISION     "202003250000Z"
         DESCRIPTION  "v3.41 add hwIntegratedPowerFault,  hwIntegratedPowerFault." 

         REVISION     "202001151623Z"
         DESCRIPTION  "v3.41 add hwBoardSoftwareNotSupport, hwVirtualLicenseExpResume,  hwSystemConfigNotMatchTrap." 

         REVISION     "202001080000Z"
         DESCRIPTION  "v3.40 add hwBoardOffline." 

         REVISION     "202001040000Z"
         DESCRIPTION  "v3.39 add hwOpticalBiasCurrentAlarm, hwOpticalBiasCurrentAlarmResume." 

         REVISION     "202001030000Z"
         DESCRIPTION  "v3.38 add hwBootloaderPwdEmpty, hwBootloaderPwdEmptyResume." 

         REVISION     "201912310000Z"
         DESCRIPTION  "v3.37 add hwPortInvalid."
		 
         REVISION     "201911250000Z"
         DESCRIPTION  "v3.36 add hwCardPortInvalid."

         REVISION     "201909300000Z"
         DESCRIPTION  "v3.35 add hwProcessName, hwEntityFileSystemFdAlarm, hwEntityFileSystemFdResume"

         REVISION     "201909170000Z"
         DESCRIPTION  "v3.34 Modify trap node hwBiosOrBootloaderPwdError, hwBiosOrBootloaderPwdErrorResume"

         REVISION     "201909160000Z"
         DESCRIPTION  "v3.33 Modify trap node hwSystemRollback. "

         REVISION     "201905150000Z"
         DESCRIPTION  "V3.32, add hwIOSwitchAlarm,hwIOSwitchAlarmResume. "         

         REVISION      "201903220000Z"
         DESCRIPTION  "v3.31 Add trap node hwCmuFail, hwCmuFailResume."       

         REVISION      "201812130000Z"
         DESCRIPTION  "v3.30 Modify trap node hwEntityFileSystemAbnormal."         

         REVISION      "201812040000Z"
         DESCRIPTION  "v3.30 Add object node hwVirtualLicenseItemName."       

         REVISION      "201811300000Z"
         DESCRIPTION  "v3.28 Add trap node hwEntityHardwareFaultAbnormal."
        
         REVISION      "201811280000Z"
         DESCRIPTION  "v3.27 Add trap node hwEntityFileSystemAbnormal."

         REVISION     "201811230000Z"
         DESCRIPTION  "v3.26 Add trap node hwEntityFileSystemRebuild."

         REVISION     "201811080000Z"
         DESCRIPTION  "v3.25 Add trap node hwNPResourceExcAlarm, hwNPResourceExcResume."

         REVISION     "201811060000Z"
         DESCRIPTION  "v3.24 Add trap node hwNPDomainDropCauseCntNumabruptlyAlarm, hwNPDomainDropCauseCntNumabruptlyResume, add object node hwLpuSlotId,hwLpuFeId and hwDropCauseId."

         REVISION     "201811050000Z"
         DESCRIPTION  "v3.23, Add trap node hwVirtualLicenseNearDeadline, hwVirtualLicenseExpire; Add object node hwLicenseRemainTime."
				
         REVISION     "201810081630Z"               
         DESCRIPTION  "V3.22, Add trap node hwCpuFail, hwCpuFailResume."	

         REVISION     "201809121630Z"               
         DESCRIPTION  "V3.21, Add trap node hwDiskBadPyhsicalBlocks, hwDiskErasePyhsicalBlocks, hwEntityConfigurationTrap."

		 REVISION     "201807021630Z"               
         DESCRIPTION  "V3.19, Add trap node hwTmPerformanceALarm, hwTmPerformanceResume."

		 REVISION     "201806052000Z"               
         DESCRIPTION  "V3.19, Add trap node hwBoardUpCoverAlarm, hwBoardUpCoverResume."
		 
		 REVISION     "201805192000Z"               
         DESCRIPTION  "V3.18, Add the objects of RPS Trap Node."
		 
         REVISION     "201805082000Z"               
         DESCRIPTION  "V3.17, Add the objects of hwEntityNpsQuality. Add trap node hwEntityNpsBaseLinkSubhealthy, hwEntityNpsBaseLinkSubhealthyResume."
	
		 REVISION     "201804202000Z"               
         DESCRIPTION  "V3.16, Add trap node hwAllLpuSfuFail, hwAllLpuSfuFailResume."

         REVISION     "201804200000Z"               
         DESCRIPTION  "V3.15, Add trap node hwEntityNpsTrapObject, hwEntityNpsTrap."

         REVISION     "201803290000Z"               
         DESCRIPTION  "V3.14, Add trap node hwReportSyslogInfo"

         REVISION     "201803200000Z"               
         DESCRIPTION  "V3.13, Add trap node hwPduNotPresent, hwPduPresent, hwPduCommLost, hwPduCommLostResume, hwPduDmuHardwareFault, hwPduDmuHardwareFaultResume,
         hwPduDMUAutoUpgradeFail, hwPduDMUAutoUpgradeFailResume, hwPduDacsHardwareFault, hwPduDacsHardwareFaultResume, 
         hwPduDacsTempAlarm, hwPduDacsTempAlarmResume, hwPduDacsI2CChannelFault, hwPduDacsI2CChannelFaultResume."

         REVISION     "201803140000Z"
         DESCRIPTION  "V3.12, Add trap node hwSMSReboot."

         REVISION     "201801150000Z"               
         DESCRIPTION  "V3.11, Modify the description"

         REVISION     "201712290000Z"               
         DESCRIPTION  "V3.10, add the objects of hwCapCPUThresholdType, hwCapCPUThresholdValue, hwCapCPUThresholdCurrent and the traps of hwCapCPUUtilizationResume, hwCapCPUUtilizationRising."

         REVISION     "201712280000Z"               
         DESCRIPTION  "V3.09, add hwPowerWorkMode hwExpectPowerWorkMode hwPowerInsufficient hwPowerInsufficientResume."

         REVISION     "201712260000Z"               
         DESCRIPTION  "V3.08, add hwPowerCubeFaulty hwPowerCubeFaultyResume."
        
        REVISION     "201712200000Z"               
         DESCRIPTION  "V3.07, add hwRTULicenseActSuccess."

         REVISION     "201712060000Z"               
         DESCRIPTION  "V3.06, modify hwPartitionThresholdCurrent to hwPartitionUseage,
hwPartitionThresholdWarning to hwPartitionUseageThreshold,
hwDiskPartitionUtilizationRising to hwDiskPartitionUseageRising,
hwDiskPartitionUtilizationResume to hwDiskPartitionUseageResume"
         REVISION     "201712010000Z"               
         DESCRIPTION  "V3.04, add the trap list of hwBoardFail and hwBoardWarning"

         REVISION     "201711300000Z"               
         DESCRIPTION  "V3.04, add hwBoardID, hwBoardAdd and hwBoardDelete."

         REVISION     "201711140000Z"               
         DESCRIPTION  "V3.03, add hwCardInconsistent"

         REVISION     "201711040000Z"
         DESCRIPTION  "V3.02, add the trap list of hwBoardInvalid"

         REVISION     "201709260000Z"
         DESCRIPTION  "V3.01, modify hte description of HwPartitionEntry; delete hwStorageEntName, hwStorageEntSpaceFree"

         REVISION     "201709260000Z"
         DESCRIPTION  "V3.00, add HwPartitionEntry; delete hwStorageEntName, hwStorageEntSpaceFree"

         REVISION     "201709210000Z"
         DESCRIPTION  "V2.85, delete hwVPortDown,hwVPortUp and vNetID"

         REVISION     "201709010000Z"
         DESCRIPTION  "V2.84, add theHiGigLinkOnTheBoardFailed"

         REVISION     "201708130000Z"
         DESCRIPTION  "V2.83, modify the parameter of hwBoardlowmemoryoverload and hwBoardlowmemoryoverloadResume"
 
         REVISION     "201707240000Z"
         DESCRIPTION  "V2.82, add the trap list of hwPowerFail and add hwBoardlowmemoryoverload and add hwBoardlowmemoryoverloadResume"

         REVISION     "201707130000Z"
         DESCRIPTION  "V2.81, add the trap of hwUpsFaultTrap and hwUpsFaultResume and hwUpsPowerLow and hwUpsPowerFull"

         REVISION     "201706140000Z"
         DESCRIPTION  "V2.80, add the trap of hwVfpSysCheckErr and hwVfpSysCheckErrResume"

         REVISION     "201706140000Z"
         DESCRIPTION  "V2.79, add the trap of hwInsSpaceLackAlarm and hwInsSpaceLackResume"

         REVISION     "201706070000Z"
         DESCRIPTION  "V2.78, add the trap of hwDataplaneCpuOverloadAlarm and hwDataplaneCpuOverloadResume"

         REVISION     "201706050000Z"
         DESCRIPTION  "V2.77, add the trap of hwOptCfgNotMatch  and hwOptCfgNotMatchResume"

         REVISION     "201706020000Z"
         DESCRIPTION  "V2.76, add the hwOptCfgNotMatch and hwOptCfgNotMatchResume"

         REVISION     "201702280000Z"
         DESCRIPTION  "V2.75, add the hwBoardEntityPowerOff"

         REVISION     "201702230000Z"
         DESCRIPTION  "V2.74, add the hwPatchDelNeedReStartTrap"


         REVISION "201702211900Z"		-- FEBRUARY 21, 2017 at 19:00 GMT
         DESCRIPTION  "V2.73, add the objects of hwBoardFail,hwBrdTempAlarm,hwBrdTempFatalAlarm,hwCardFail,hwChassisInvalid,hwPowerFail " 

         REVISION "201702130900Z"		
         DESCRIPTION  "V2.72, add hwBoardPortsConflict " 

	 REVISION "201702100000Z"		
         DESCRIPTION  "V2.71, add hwBoardWarning and hwBoardWarningResume " 

         REVISION "201612232100Z"		
         DESCRIPTION  "V2.70, modify the content of hwEntityBandwidthMode " 


        REVISION "201611282100Z"		-- November 28, 2016 at 21:00 GMT
         DESCRIPTION  "V2.69, add hwPortOpticalPositionInvalid ,hwPortOpticalPositionValid " 
		 
		 REVISION "201611232100Z"		-- November 23, 2016 at 21:00 GMT
         DESCRIPTION  "V2.68, add hwEntityTrapReasonDescr as VB binder under 'hwOpticalUnAuthorized' "

         REVISION     "201610252100Z"
         DESCRIPTION  "V2.67,add object  'hwGpsModuleRemove,hwGpsModuleInsert ' of hwOpticalTrap "
		
         REVISION     "201610211400Z"
         DESCRIPTION  "V2.66,add object  'hwNeedModifyCfgTrap' of hwBoardTrap "
		 
         REVISION     "201608171400Z"
         DESCRIPTION  "V2.65,add object  'hwEntityTrapReasonDescr' of hwPmuFail "

         REVISION     "201608031400Z"
         DESCRIPTION  "V2.64,hwEntitySplitChange, hwCardSplitChange"
			
         REVISION     "201607221000Z"
         DESCRIPTION  "V2.63, add hwEntityBandwidthMode, hwCardBandwidthModeChange" 
         
         REVISION     "201607151000Z"
         DESCRIPTION  "V2.62, modify the parament of hwVPortDown"      

         REVISION     "201607121000Z"
         DESCRIPTION  "V2.61, modify 2 error code description of 135184 and 144130 for compile warnings"         

         REVISION     "201607041000Z"
         DESCRIPTION  "V2.60, add hwFanMinorAlarm, hwFanMinorAlarmResume"

         REVISION     "201604151000Z"
         DESCRIPTION  "V2.59, add hwDiskPartitionInValid, hwDiskPartitionInValidResume, hwDiskPartitionSpacinsufficient, hwDiskPartitionSpacinsufficientResume, hwDiskPartitionUtilizationRising, hwDiskPartitionUtilizationResume"
         
        REVISION     "201604141000Z"
         DESCRIPTION  "V2.58, modify the Name of hwVMResourceInconsist and hwVMResourceInconsistResume to hwVMResInconsist and hwVMResInconsistResume, add the Object vmName to hwVMResInconsist and hwVMResInconsistResume"

         REVISION     "201604111000Z"
         DESCRIPTION  "V2.57, add hwVBoardInvalid modify the objects of hwVPortDown."
         
         REVISION     "201603031000Z"
         DESCRIPTION  "V2.56, add hwDiskTrap."

         REVISION     "201603010000Z"
         DESCRIPTION  "V2.55, modify the Description of  hwPinchCardResetResume."

         REVISION     "201602290000Z"
         DESCRIPTION  "V2.54, add hwVMResourceInconsist,hwVMResourceInconsistResume"

         REVISION     "201602180000Z"
         DESCRIPTION  "V2.53, add hwPinchCardReset,hwPinchCardResetResume. " 

         REVISION     "201601040000Z"
         DESCRIPTION  "V2.52, add hwVportDown,hwVPortUp and a parameter vNetID. " 

         REVISION     "201512290000Z"
         DESCRIPTION  "V2.51, modify the Description of  hwChassisFailResume. " 

         REVISION     "201512160000Z"
         DESCRIPTION  "V2.50, add hwThreadTrap, hwThreadFaultIsolate. " 

         REVISION     "201511030000Z"
         DESCRIPTION  "V2.49, modify the Description of hwBandwidthOfAllCardsExceedsThresholdResume, add hwBandwidthOfAllCardsExceedsThresholdFatalAlarm, hwBandwidthOfAllCardsExceedsThresholdFatalResume" 

		 REVISION     "201510100000Z"
         DESCRIPTION  "V2.48, add hwVirtualAccessDrvConfigError" 
		 
         REVISION     "201509300000Z"
         DESCRIPTION  "V2.47, add hwBandwidthOfAllCardsExceedsThresholdAlarm, hwBandwidthOfAllCardsExceedsThresholdResume" 

         REVISION     "201509170000Z"
         DESCRIPTION  "V2.46, add HWTrapProbableCause and change the hwEntityTrapFaultID " 
         
         REVISION     "201506160000Z"
         DESCRIPTION  "V2.45, add hwEntityTrapReasonDescr to hwPowerInvalid and hwPowerInvalidResume. " 
         
         REVISION     "201505210000Z"
         DESCRIPTION  "V2.44, add hwBoardHeartbeatTimeout, hwBoardHeartbeatResume. " 

         REVISION     "201505160000Z"
         DESCRIPTION  "V2.43, add hwPortRemove, hwPortInsert, hwCardResExceed, hwCardResExceedResume. " 
         
         REVISION     "201505150000Z"
         DESCRIPTION  "V2.42, add hwBoardResetByCmd, hwBoardResetByCmdResume, hwCardResetByCmd, hwCardResetByCmdResume. " 

         REVISION     "201503130000Z"
         DESCRIPTION  "V2.41, add hwOpticalVendorName and hwOpticalVendorSN as VB binder under hwOpticalInsert, hwOpticalRemove"

                                   REVISION     "201501280000Z"
         DESCRIPTION  "V2.40, add hwEntityTrapReasonDescr as VB binder under hwFanFail, hwFanFailResume"

                                    REVISION     "201412100000Z"
         DESCRIPTION  "V2.39, add hwUsbOperType, hwUsbStatusChg"

		 REVISION     "201412010000Z"
         DESCRIPTION  "V2.38, add hwEntityTrapReasonDescr as VB binder under hwPowerFail, hwPowerFailResume"

		 REVISION     "201410280000Z"
         DESCRIPTION  "V2.37, add hwEntityTrapReasonDescr as VB binder under hwFanInvalid , hwFanInvalidResume"
	
		 REVISION     "201410130000Z"
         DESCRIPTION  "V2.36, delete the content modified in V2.35 to rollback to V2.34"		
				
		 REVISION     "201410090000Z"
         DESCRIPTION  "V2.35, add ifindex as VB binder under hwOpticalRemove, hwOpticalInsert, hwPortDown, hwPortUp"
		 
		 REVISION     "201409010000Z"
         DESCRIPTION  "V2.34, add one or two objects under part trap nodes on hwChassisTrap, hwBoardTrap, hwCardTrap, hwFanTrap, hwPowerTrap, hwPortTrap"		
				
         REVISION     "201406280000Z"
         DESCRIPTION  "V2.33, add  hwBandwidthOfAllCardsExceedsThreshold"

        REVISION     "201405190000Z"
           DESCRIPTION  "V2.32, modify the Description of hwPortDownReason,"

         REVISION     "201405190000Z"
           DESCRIPTION  "V2.31, "	

         REVISION     "201403280000Z"
           DESCRIPTION  "V2.30, "	

         REVISION     "201401040000Z"
           DESCRIPTION  "V2.29, "	

        REVISION     "201311211111Z"
        DESCRIPTION  "V2.28, add hwRateofTraffic"

        REVISION     "201307041705Z"
        DESCRIPTION  "V2.27, add hwEntityDyingGsapEvent"

        REVISION     "201307021621Z"
        DESCRIPTION  "V2.26, add hwBoardPowerOff"

        REVISION     "201306251411Z"
        DESCRIPTION  "V2.25, add hwPortDownReason"

        REVISION     "201306071107Z"
        DESCRIPTION  "V2.24, add hwIOSwitchOneAlarm,hwIOSwitchOneAlarmResume,hwIOSwitchTwoAlarm,hwIOSwitchTwoAlarmResume,hwIOSwitchThreeAlarm,hwIOSwitchThreeAlarmResume. " 

        REVISION     "201305280000Z"
        DESCRIPTION  "V2.23, add hwUSBUnidentified,hwUSBUnidentifiedResume  " 

        REVISION     "201304131452Z"
           DESCRIPTION  "V2.22, add hwOpticalTunableNotMatch and hwOpticalTunableNotMatchResume, "
           
        REVISION     "201303181421Z"
           DESCRIPTION  "V2.21, add the hwLaserNoFited,hwLaserNoFitedResume, "
   
         REVISION     "201201250000Z"
           DESCRIPTION  "V2.20, add  the hwPmuRemove,hwPmuInsert,hwPmuFail,hwPmuFailResume,hwPmuInvalid,hwPmuInvalidResume, "

                                                                   ::= { hwDatacomm 219 } 
--
-- Node definitions
--

--
-- definition of the root cause for the Huawei proprietary traps
--
	HWTrapProbableCause ::= TEXTUAL-CONVENTION
	    STATUS current
	    DESCRIPTION
	        "This list contains the root reasons of the Huawei proprietary traps."
	    SYNTAX         INTEGER
	            {
			-- 152065: The device is powered off unexpectedly
			theDeviceIsPoweredOffUnexpectedly  (152065),
			-- 152066: The file system is damaged
			theFileSystemIsDamaged (152066),
			-- 152070:  The MBR partition table of SATA is damaged
			theMBRPartitionTableOfSATAIsDamaged  (152070),
			-- 157952:  Remote alarm indication on E1 port
			remoteAlarmIndicationOnE1Port	(157952),
			-- 157953:  An alarm indication of the upstream E1 signals
			anAlarmIndicationOfTheUpstreamE1Signals	(157953),
			-- 157954:  Loss of frame alignment alarm on E1 port
			lossOfFrameAlignmentAlarmOnE1Port	(157954),
			-- 157955:  Loss of multiframe alignment on E1 port
			lossOfMultiframeAlignmentOnE1Port	(157955),
			-- 131072:  Reseted Frame Register
			resetedFrameRegister	(131072),
			-- 131328:  The Air Filter Inside The Chassis Was Not Cleaned
			theAirFilterInsideTheChassisWasNotCleaned	(131328),
			-- 131329:  The Chassis Links Few
			theChassisLinksFew	(131329),
			-- 131330:  MPU Board Insufficiency
			mPUBoardInsufficiency	(131330),
			-- 131331:  A GTL License For A 10GE NPUI-20 Is Activated, But The 10GE Interface Is Not Activated Using The Active 10ge-interface Command In The Slot View
			aGTLLicenseForA10GENPUI20IsActivatedButThe10GEInterfaceIsNotActivatedUsingTheActive10geInterfaceCommandInTheSlotView	(131331),
			-- 131333:  The Type Of Power Or Fan Is Inconsistent
			theTypeOfPowerOrFanIsInconsistent	(131333),
			-- 131334:  SFU Board And The LPU Board Did Not Match
			sFUBoardAndTheLPUBoardDidNotMatch	(131334),
			-- 131335:  The 40G Boards And The Power And Fan Modules Did Not Match
			the40GBoardsAndThePowerAndFanModulesDidNotMatch	(131335),
			-- 131336:  Chassis Power Supply Insufficiency
			chassisPowerSupplyInsufficiency	(131336),
			-- 131337:  All SFU Boards Removed
			allSFUBoardsRemoved	(131337),
			-- 131338:  All LPU Boards Removed
			allLPUBoardsRemoved	(131338),
			-- 131339:  All CMU Boards Removed
			allCMUBoardsRemoved	(131339),
			-- 131340:  The power module types are inconsistent
			thePowerSupplyModuleMismatch	(131340),
			-- 131341:  Fail To Get The Slot Information Of The Power Supply Module
			failToGetTheSlotInformationOfThePowerSupplyModule	(131341),
			-- 131342:  Average Current Bus Not Installed
			averageCurrentBusNotInstalled	(131342),
			-- 131343:  Power Supply Abnormal Due To Too Many Fans In The Frame
			powerSupplyAbnormalDueToTooManyFansInTheFrame	(131343),
                        -- 131360:  The number of detected SFUs does not meet requirements
			theNumberOfSfuBoardNotEnough	(131360),
                        -- 131367:  The fan module types are inconsistent
                        theFanSupplyModuleMismatch	(131367),
			-- 131585:  The Number Of Registered SFUs Is Smaller Than The Minimum Number Of SFUs That Must Be Configured
			theNumberOfRegisteredSFUsIsSmallerThanTheMinimumNumberOfSFUsThatMustBeConfigured	(131585),
			-- 131586:  SFU Board Dismatch The Frame
			sFUBoardDismatchTheFrame	(131586),
			-- 131587:  The Slave Board Type Mismatches The Master
			theSlaveBoardTypeMismatchesTheMaster	(131587),
			-- 131588:  Right License Unavailable, Boards Or Cards Will Be Reset After 72 hrs
			rightLicenseUnavailableBoardsOrCardsWillBeResetAfter72hrs	(131588),
			-- 131589:  Right License Will Expire, Then boards Or Cards Will Be Reset Every 24 hrs
			rightLicenseWillExpireThenboardsOrCardsWillBeResetEvery24hrs	(131589),
			-- 131590:  Right License Unavailable, Boards Or Cards Will Be Reset Every 24 hrs
			rightLicenseUnavailableBoardsOrCardsWillBeResetEvery24hrs	(131590),
			-- 131840:  The Board Was Removed
			theBoardWasRemoved	(131840),
			-- 131842:  BTB Insert Two MPU Board
			bTBInsertTwoMPUBoard	(131842),
			-- 132096:  Power Supply For A Board Was Abnormal
			powerSupplyForABoardWasAbnormal	(132096),
			-- 132097:  The MonitorBus Of The Board Partially Failed
			theMonitorBusOfTheBoardPartiallyFailed	(132097),
			-- 132098:  The SC Chip On The Board Partially Failed
			theSCChipOnTheBoardPartiallyFailed	(132098),
			-- 132099:  The TM Chip On The Board Partially Failed
			theTMChipOnTheBoardPartiallyFailed	(132099),
			-- 132100:  The Board Was Not Installed Into A Proper Slot
			theBoardWasNotInstalledIntoAProperSlot	(132100),
			-- 132101:  The 48 V Power Supply For The Board Was Abnormal
			the48VPowerSupplyForTheBoardWasAbnormal	(132101),
			-- 132102:  The Board Cannot Be Properly Powered On Or Powered Off
			theBoardCannotBeProperlyPoweredOnOrPoweredOff	(132102),
			-- 132103:  The Battery Of The MPU Failed
			theBatteryOfTheMPUFailed	(132103),
			-- 132104:  The Board Obtained Abnormal Signals From The Master And Slave MPUs
			theBoardObtainedAbnormalSignalsFromTheMasterAndSlaveMPUs	(132104),
			-- 132105:  The Sensor On The Board Failed
			theSensorOnTheBoardFailed	(132105),
			-- 132106:  The Flash Memory On The Board Failed
			theFlashMemoryOnTheBoardFailed	(132106),
			-- 132107:  The PHY Chip On The Board Partially Failed
			thePHYChipOnTheBoardPartiallyFailed	(132107),
			-- 132108:  Clock Signals On The Board Were Faulty
			clockSignalsOnTheBoardWereFaulty	(132108),
			-- 132109:  The Voltage Of The Board Exceeded The Upper Fatal Threshold
			theVoltageOfTheBoardExceededTheUpperFatalThreshold	(132109),
			-- 132110:  The Voltage Of The Board Exceeded The Upper Warning Threshold
			theVoltageOfTheBoardExceededTheUpperWarningThreshold	(132110),
			-- 132111:  The Voltage Of The Board Was Lower Than The Lower Fatal Threshold
			theVoltageOfTheBoardWasLowerThanTheLowerFatalThreshold	(132111),
			-- 132112:  The Voltage Of The Board Was Lower Than The Lower Warning Threshold
			theVoltageOfTheBoardWasLowerThanTheLowerWarningThreshold	(132112),
			-- 132113:  The Current Of The Board Exceeded The Upper Fatal Threshold
			theCurrentOfTheBoardExceededTheUpperFatalThreshold	(132113),
			-- 132114:  The Current Of The Board Was Higher Than The Higher Warning Threshold
			theCurrentOfTheBoardWasHigherThanTheHigherWarningThreshold	(132114),
			-- 132115:  The Current Of The Board Was Lower Than The Lower Fatal Threshold
			theCurrentOfTheBoardWasLowerThanTheLowerFatalThreshold	(132115),
			-- 132116:  The Current For The Board Was Lower Than The Lower Warning Threshold
			theCurrentForTheBoardWasLowerThanTheLowerWarningThreshold	(132116),
			-- 132117:  Board Clock Source Failure
			boardClockSourceFailure	(132117),
			-- 132118:  The In-position Signal Of The Board Failed
			theInPositionSignalOfTheBoardFailed	(132118),
			-- 132119:  The MonitorBus Of The Board Failed
			theMonitorBusOfTheBoardFailed	(132119),
			-- 132120:  The IIC Bus Of The Board Failed
			theIICBusOfTheBoardFailed	(132120),
			-- 132121:  The USB Controller On The Board Failed
			theUSBControllerOnTheBoardFailed	(132121),
			-- 132122:  The CF Card Of The Board Failed
			theCFCardOfTheBoardFailed	(132122),
			-- 132123:  The NVRAM Of The Board Failed
			theNVRAMOfTheBoardFailed	(132123),
			-- 132124:  The I2C Bus Malfunctions
			theI2CBusMalfunctions	(132124),
			-- 132125:  The GE Data Bus Malfunctions
			theGEDataBusMalfunctions	(132125),
			-- 132126:  The FE Data Bus Malfunctions
			theFEDataBusMalfunctions	(132126),
			-- 132127:  The Board Clock Malfunctions
			theBoardClockMalfunctions	(132127),
			-- 132128:  The Board PLL Malfunctions
			theBoardPLLMalfunctions	(132128),
			-- 132129:  The FE PHY Chip Malfunctions
			theFEPHYChipMalfunctions	(132129),
			-- 132130:  The GE PHY Chip Malfunctions
			theGEPHYChipMalfunctions	(132130),
			-- 132131:  The DSP Malfunctions
			theDSPMalfunctions	(132131),
			-- 132134:  LANSWITCH Abnormal
			lANSWITCHAbnormal	(132134),
			-- 132135:  The LLP Malfunctions
			theLLPMalfunctions	(132135),
			-- 132136:  The ASIC Malfunctions
			theASICMalfunctions	(132136),
			-- 132137:  The Chip Malfunctions
			theChipMalfunctions	(132137),
			-- 132139:  The Voltage Of The Subcard Exceeded The Upper Fatal Threshold
			theVoltageOfTheSubcardExceededTheUpperFatalThreshold	(132139),
			-- 132140:  The Voltage Of The Subcard Exceeded The Upper Warning Threshold
			theVoltageOfTheSubcardExceededTheUpperWarningThreshold	(132140),
			-- 132141:  The Voltage Of The Subcard Was Lower Than The Lower Fatal Threshold
			theVoltageOfTheSubcardWasLowerThanTheLowerFatalThreshold	(132141),
			-- 132142:  The Voltage Of The Subcard Was Lower Than The Lower Warning Threshold
			theVoltageOfTheSubcardWasLowerThanTheLowerWarningThreshold	(132142),
			-- 132144:  The Software Package In CFCARD May Be Lost Or Abnormal
			theSoftwarePackageInCFCARDMayBeLostOrAbnormal	(132144),
			-- 132145:  Pos Card Fault
			posCardFault	(132145),
			-- 132146:  POE Fault
			pOEFault	(132146),
			-- 132147:  LIGHT Fault
			lIGHTFault	(132147),
			-- 132148:  Board Fault
			boardFault	(132148),
			-- 132149:  The ECU Board Chip Is Abnormal
			theECUBoardChipIsAbnormal	(132149),
			-- 132150:  The CFcard Storage Media Of MPU Exceeded The Prealarm Threshold
			theCFcardStorageMediaOfMPUExceededThePrealarmThreshold	(132150),
			-- 132151:  WLAN Fault
			wLANFault	(132151),
			-- 132152:  Board CPU Fault
			boardCPUFault	(132152),
			-- 132153:  The Electronic Switch For Channel Selection Malfunctions
			theElectronicSwitchForChannelSelectionMalfunctions	(132153),
			-- 132154:  Voice Board Fault
			voiceBoardFault	(132154),
			-- 132155:  The Internal Data Channel Of The Board Malfunctions
			theInternalDataChannelOfTheBoardMalfunctions	(132155),
			-- 132156:  Board RDRAM Memory Fault
			boardRDRAMMemoryFault	(132156),
			-- 132157:  Multicast Capability Of The Traffic Management Chip Was Insufficient
			multicastCapabilityOfTheTrafficManagementChipWasInsufficient	(132157),
			-- 132158:  Service Pinch Card Fault
			servicePinchCardFault	(132158),
			-- 132159:  Board Work Mode Dismatch Power Too High
			boardWorkModeDismatchPowerTooHigh	(132159),
			-- 132160:  Board Work Mode Dismatch Power Too Low
			boardWorkModeDismatchPowerTooLow	(132160),
			-- 132161:  Board Temperature Sensor Fault
			boardTemperatureSensorFault	(132161),
			-- 132162:  Fan Or Power Dismatch Device
			fanOrPowerDismatchDevice	(132162),
			-- 132163:  Board CPU Single Core Fault
			boardCPUSingleCoreFault	(132163),
			-- 132164:  Too Many Sensor Points Are Failed
			tooManySensorPointsAreFailed	(132164),
			-- 132165:  Board HIG Bus Error
			boardHIGBusError	(132165),
			-- 132166:  Failed To Get The Board ESN
			failedToGetTheBoardESN	(132166),
			-- 132167:  The Memory Size Is Different From The Rated
			theMemorySizeIsDifferentFromTheRated	(132167),
			-- 132168:  The Non-core Chip Of The Board Fault
			theNonCoreChipOfTheBoardFault	(132168),
			-- 132169:  Board Communication Channel Error
			boardCommunicationChannelError	(132169),
			-- 132170:  Board RTC Error
			boardRTCError	(132170),
			-- 132171:  Line Rate Unreachable On The Board
			lineRateUnreachableOnTheBoard	(132171),
			-- 132172:  Loss Of Heart Beat Exceeds The Threshold
			lossOfHeartBeatExceedsTheThreshold	(132172),
			-- 132173:  Security Acceleration Engine Is Abnormal
			securityAccelerationEngineIsAbnormal	(132173),
			-- 132174:  PCB Corrosive
			pCBCorrosive	(132174),
			-- 132177:  Interface MAC CRC Error
			interfaceMACCRCError	(132177),
			-- 132178:  E-label CRC Error
			e-labelCRCError	(132178),
			-- 132182:  Board Voltage Sensors Fault
			boardVoltageSensorsFault	(132182),
			-- 132183:  Voltage A/D Fault
			voltageADFault	(132183),
			-- 132184:  SPI Bus Fault
			sPIBusFault	(132184),
			-- 132202:  The 38M clock fails
			the38MClockFails	(132202),
			-- 132205:  The HiGig Link On The Board Failed
			theHiGigLinkOnTheBoardFailed	(132205),
			-- 132207:  The board clock fails
			theBoardClockFails	(132207),
			-- 132208:  A DDR fault occurs on the board
			aDDRFaultOccursOnTheBoard	(132208),
			-- 132209:  The slot ID of the board fails to be checked
			theSlotIdOfTheBoardFailsToBeChecked	(132209),
			-- 132212:  Access to the flash memory of the board fails
			accessToTheFlashMemoryOfTheBoardFails	(132212),
			-- 132213:  The external TCAM chip could not be accessed
			theexternalTCAMchipcouldnotbeaccessed	(132213),
			-- 132214:  The active and standby MPUs cannot communicate with each other
			theActiveAndStandbyMpusCannotCommunicateWithEachOther	(132214),
			-- 132221:  The board type cannot be identified
			theBoardTypeCanNotBeIdentified	(132221),
			-- 132272:  The Chip is failed
			theChipIsFailed	(132272),
			-- 132279:  Failed to check the voltage of the board
			failedToCheckTheVoltageOfTheBoard	(132279),
			-- 132285:  The disk will soon become invalid
			theDiskWillSoonBecomeInvalid	(132285),
			-- 132286:  A HTM chip fault occurred
			aHTMChipFaultOccurred	(132286),
			-- 132287:  The frequency synthesizer failed
			theFrequencySynthesizerFailed	(132287),
			-- 132290:  The slot ID signal from the CANBUS is abnormal
			slotIdSignalFromCanbusIsAbnormal	(132290),
			-- 132293:  CANBUS communications between the monitor chips failed
			canbusCommunicationsBetweenTheMonitorChipsFailed	(132293),
			-- 132296:  Overcurrent occurred on the board
			overcurrentOccurredOnTheBoard	(132296),
			-- 132297:  The FPGA is abnormal
			theFPGAIsAbnormal	(132297),
			-- 132298:  The sensor chip on the board was faulty
			theSensorChipOnTheBoardWasFaulty	(132298),
			-- 132313:  A voltage drop occurred on the board
			aVoltageDropOccurredOnTheBoard	(132313),
			-- 132314:  The serial management bus of the board malfunctions
			theSerialManagementBusOfTheBoardMalfunctions	(132314),
			-- 132319:  Failed to access backplane IIC
			failedToAccessBackPlaneIIC	(132319),
			-- 132320:  Failed to check backplane ID
			failedToCheckBackPlaneID	(132320),
			-- 132321:  The IIC of MCU module is abnormal
			theIICOfMcuModuleIsAbnormal	(132321),
			-- 132323:  The 19M clock fails
			the19MClockFails	(132323),
			-- 132324:  The board clock(156M) failed
			theBoard156MClockFailed	(132324),
			-- 132325 The device certificate verification failed
			deviceCertificateVerifyFail              (132325),
            -- 132326:  The system memory overload
            theSystemMemoryOverload	(132326),
            -- 132327:  The NAND Of Chip Was Faulty
            theNandOfChipWasFaulty	(132327),
			-- 132315:  The negotiated rate level of the SATA disk does not meet the requirement
			theSataRateLevelIsAbnormal	(132315),
			-- 132316:  The remaining life of SATA is not enough
			theSataRemainLifeNotEnough	(132316),
			-- 132317:  The SATA is abnormal
			theSataIsAbnormal	(132317),
			-- 132318:  The SATA permission becomes read-only
			theSataIsReadOnly	(132318),
			-- 132330:  Port received package with preamble code error
			portReceivePreambleCodeErrorPackage	(132330),
			-- 132331:  Port cannot go up due to lack of serdes mode
			portCannotGoUpDueToLackOfSerdesMode	(132331),
			-- 132332:  The system disk will soon become invalid
			theSystemDiskWillSoonBecomeInvalid	(132332),
			-- 132333:  The data disk will soon become invalid
			theData-DiskWillSoonBecomeInvalid	(132333),
			-- 132334:  The negotiation rate level of the disk does not meet the requirements
			theNegotiationRateLevelOfTheDiskDoesNotMeetTheRequirements	(132334),
			-- 132335:  SATA is abnormal
			sataIsAbnormal	(132335),
			-- 132347:  Failed to check the voltage of the card
			failedToCheckTheVoltageOfTheCard	(132347),
			-- 132348:  E1 framer was faulty
			e1FramerWasFaulty	(132348),
			-- 132349:  LTE module was faulty
			lteModuleWasFaulty	(132349),
			-- 132350:  The FULLIN signal of the board is abnormal
			theFullinSignalOfTheBoardIsAbnormal	(132350),
			-- 132351:  A SerialCpldLocalbus fault occurs on the board
			aSerialCpldLocalbusFaultOccursOnTheBoard	(132351),
			-- 132352:  The micro switch of the board fails
			theMicroSwitchOfTheBoardFails	(132352),
			-- 132353:  USB overcurrent occurred
			usbOvercurrentOccurred	(132353),
			-- 132354:  The power supply self-check failed
			thePowerSupplySelfCheckFailed	(132354),
			-- 132357:  Power IIC failed
			thePowerIICFailed (132357),
			-- 132369:  5G module was faulty
			fifthGenerationModuleWasFaulty	(132369),
			-- 132382:  A CRC error occurred on the XFI interface
			aCRCErrorOccurredOnTheXFIInterface     (132382),
			-- 132383:  An error occurred when the MPU delivers the ACT signals to all LPU and SFU
			anErrorOccurredWhenTheMPUDeliversTheACTSignalsToAllLPUAndSFU     (132383),
                        --132385:  The Optical Modules Inserted Into The Optical Ports Have More Than Two Speeds
			TheOpticalModulesInsertedIntoTheOpticalPortsHaveMoreThanTwoSpeeds     (132385),
                        --132386:  The Speeds Of Optical Modules Inserted Into Optical Ports Are Both 10G And 2500M
			TheSpeedsOfOpticalModulesInsertedIntoOpticalPortsAreBoth10GAnd2500M     (132386),
			-- 132425:  The FPGA1 logic of the board is abnormal
			theFPGA1logicoftheboardisabnormal	(132425),
                        -- 132426:  The FPGA2 logic of the board is abnormal
			theFPGA2logicoftheboardisabnormal	(132426),
                        -- 132427:  The FPGA3 logic of the board is abnormal
			theFPGA3logicoftheboardisabnormal	(132427),
                        -- 132428:  The FPGA4 logic of the board is abnormal
			theFPGA4logicoftheboardisabnormal	(132428),
                        -- 132429:  The FPGA5 logic of the board is abnormal
			theFPGA5logicoftheboardisabnormal	(132429),
			-- 132608:  The Board Selfcheck Failed
			theBoardSelfcheckFailed	(132608),
			-- 132609:  Heartbeats Of The Board Were Lost And Thus The Board Was Reset
			heartbeatsOfTheBoardWereLostAndThusTheBoardWasReset	(132609),
			-- 132610:  The Board Did Not Match The Device
			theBoardDidNotMatchTheDevice	(132610),
			-- 132611:  The MAC Address Of The Board Was Abnormal
			theMACAddressOfTheBoardWasAbnormal	(132611),
			-- 132612:  Clock Synchronization Signals Failed On The Board
			clockSynchronizationSignalsFailedOnTheBoard	(132612),
			-- 132613:  The FPGA Logic Of The Board Was Faulty
			theFPGALogicOfTheBoardWasFaulty	(132613),
			-- 132614:  The EPLD Logic Of The Board Was Faulty
			theEPLDLogicOfTheBoardWasFaulty	(132614),
			-- 132711:  Board burnt due to high PoE power
			BoardBurntDueToHighPoEPower	(132711),
			-- 132615:  Signals Provided By The Clock Board Failed
			signalsProvidedByTheClockBoardFailed	(132615),
			-- 132616:  Clock Signals Failed On The Board
			clockSignalsFailedOnTheBoard	(132616),
			-- 132617:  The TM Chip On The Board Totally Failed
			theTMChipOnTheBoardTotallyFailed	(132617),
			-- 132618:  The NP Of The Board Failed
			theNPOfTheBoardFailed	(132618),
			-- 132619:  The ACT Signal On The Board Was Abnormal
			theACTSignalOnTheBoardWasAbnormal	(132619),
			-- 132620:  Power Supply For A Board Was Insufficient
			powerSupplyForABoardWasInsufficient	(132620),
			-- 132621:  The SC Chip On The Board Totally Failed
			theSCChipOnTheBoardTotallyFailed	(132621),
			-- 132622:  The SM Chip On The Board Failed
			theSMChipOnTheBoardFailed	(132622),
			-- 132623:  The TCAM Chip Of The Board Failed
			theTCAMChipOfTheBoardFailed	(132623),
			-- 132624:  Memory Of The Board Failed
			memoryOfTheBoardFailed	(132624),
			-- 132625:  The Laswitch Chip On The Board Failed
			theLaswitchChipOnTheBoardFailed	(132625),
			-- 132626:  The Board Was Powered Off
			theBoardWasPoweredOff	(132626),
			-- 132627:  Board Registration Failed
			boardRegistrationFailed	(132627),
			-- 132628:  The Board Was Reset Abnormally
			theBoardWasResetAbnormally	(132628),
			-- 132629:  The PHY Chip On The Board Totally Failed
			thePHYChipOnTheBoardTotallyFailed	(132629),
			-- 132630:  The Board Obtained Abnormal Signals From Master And Slave MPUs
			theBoardObtainedAbnormalSignalsFromMasterAndSlaveMPUs	(132630),
			-- 132631:  The Board Obtained Abnormal Signals From SFUs (functioning As Master And Slave Clock Sources)
			theBoardObtainedAbnormalSignalsFromSFUsFunctioningAsMasterAndSlaveClockSources	(132631),
			-- 132632:  The PCI Bus Of The Board Failed
			thePCIBusOfTheBoardFailed	(132632),
			-- 132633:  The Board Did Not Match The Slot
			theBoardDidNotMatchTheSlot	(132633),
			-- 132634:  The Loopback Heartbeats Of The Board Were Faulty
			theLoopbackHeartbeatsOfTheBoardWereFaulty	(132634),
			-- 132635:  The Number Of Intelligent Heartbeat Errors Reached The Board Reset Threshold
			theNumberOfIntelligentHeartbeatErrorsReachedTheBoardResetThreshold	(132635),
			-- 132636:  The Number Of Lost Intelligent Heartbeats Reached The Board Reset Threshold
			theNumberOfLostIntelligentHeartbeatsReachedTheBoardResetThreshold	(132636),
			-- 132637:  The Number Of Intelligent Heartbeat Errors Reached The Alarm Threshold
			theNumberOfIntelligentHeartbeatErrorsReachedTheAlarmThreshold	(132637),
			-- 132638:  The Number Of Lost Intelligent Heartbeats Reached The Alarm Threshold
			theNumberOfLostIntelligentHeartbeatsReachedTheAlarmThreshold	(132638),
			-- 132639:  The Board CPU Fail
			theBoardCPUFail	(132639),
			-- 132640:  The Link Between The TM Chip And The NP Chip Was Detected Faulty
			theLinkBetweenTheTMChipAndTheNPChipWasDetectedFaulty	(132640),
			-- 132641:  The TM Chip Failed The Self Check
			theTMChipFailedTheSelfCheck	(132641),
			-- 132642:  The Number Of Links Between The TM Chip And The SFU Was Too Small
			theNumberOfLinksBetweenTheTMChipAndTheSFUWasTooSmall	(132642),
			-- 132644:  The Service Logic Malfunctions
			theServiceLogicMalfunctions	(132644),
			-- 132645:  The Upper Tact Switch Is Turned On
			theUpperTactSwitchIsTurnedOn	(132645),
			-- 132646:  The Lower Tact Switch Is Turned On
			theLowerTactSwitchIsTurnedOn	(132646),
			-- 132647:  The Control Logic Malfunctions
			theControlLogicMalfunctions	(132647),
			-- 132648:  The SFU Board Is Abnormal And Can Not Be Used
			theSFUBoardIsAbnormalAndCanNotBeUsed	(132648),
			-- 132649:  The ECU Board Is Abnormal And Can Not Be Used
			theECUBoardIsAbnormalAndCanNotBeUsed	(132649),
			-- 132650:  The Logic Clock Failed
			theLogicClockFailed	(132650),
			-- 132651:  The Logic Bus Failed
			theLogicBusFailed	(132651),
			-- 132652:  The Logic Chip Failed
			theLogicChipFailed	(132652),
			-- 132653:  The Main Control Logic Malfunctions
			theMainControlLogicMalfunctions	(132653),
			-- 132654:  The Board Is Incompatible With System Software
			theBoardIsIncompatibleWithSystemSoftware	(132654),
			-- 132655:  The Logic Slotid Of The Board Is Faulty During Running Time. Please Do Not Try To Reset This Board Or Reboot This Device
			theLogicSlotidOfTheBoardIsFaultyDuringRunningTimePleaseDoNotTryToResetThisBoardOrRebootThisDevice	(132655),
			-- 132656:  The Logic Slotid Of The Board Is Faulty During Booting Time. Please Check The Board Based On The Clear Advice
			theLogicSlotidOfTheBoardIsFaultyDuringBootingTimePleaseCheckTheBoardBasedOnTheClearAdvice	(132656),
			-- 132657:  FE Dismatch Cards Combination
			fEDismatchCardsCombination	(132657),
			-- 132658:  Clock Board Master And Slave Status Invalid
			clockBoardMasterAndSlaveStatusInvalid	(132658),
			-- 132659:  Board Output Power Abnormal
			boardOutputPowerAbnormal	(132659),
			-- 132660:  Board Reset Due To Overheat Protection
			boardResetDueToOverheatProtection	(132660),
			-- 132661:  User Operation
			userOperation	(132661),
			-- 132662:  Board Service Mode Error
			boardServiceModeError	(132662),
			-- 132663:  The Core Chip Of The Board Fault
			theCoreChipOfTheBoardFault	(132663),
			-- 132664:  CPLD Logic Error
			cPLDLogicError	(132664),
			-- 132665:  Traffic Congestion Due To The Traffic Backpressure
			trafficCongestionDueToTheTrafficBackpressure	(132665),
			-- 132666:  Board Type Mismatches The Preconfiguration
			boardTypeMismatchesThePreconfiguration	(132666),
			-- 132674: The FPGA of the board failed
			theFPGAOfTheBoardFailed	(132674),
                        -- 132675: The LSW port connected to the MPU fails
                        thsLswPortConnectedToTheMpuFails                  (132675),
			-- 132677:  The FPGA localbus self-test failed
			theFPGALocalbusSelf-testFailed	(132677),
			-- 132678:  The board does not match the slot
			theBoardDoesNotMatchTheSlot	(132678),
			-- 132685:  The board is not installed properly
			theBoardIsNotInstalledProperly	(132685),
			-- 132686:  The smi serial of the board is abnormal
			theSmiSerialOfTheBoardIsAbnormal	(132686),
			-- 132690:  The FPGA1 logic of the board failed
			theFPGA1logicoftheboardfailed	(132690),
			-- 132691:  The FPGA2 logic of the board failed
			theFPGA2logicoftheboardfailed	(132691),
                        -- 132692:  The FPGA3 logic of the board failed
			theFPGA3logicoftheboardfailed	(132692),
                        -- 132693:  The FPGA4 logic of the board failed
			theFPGA4logicoftheboardfailed	(132693),
                        -- 132694:  The FPGA5 logic of the board failed
			theFPGA5logicoftheboardfailed	(132694),
			-- 132695:  The board voltage exceeds the fatal alarm threshold
			theBoardVoltageExceedsTheFatalAlarmThreshold	(132695),
			-- 132696:  The board voltage fell below the fatal alarm threshold
			theBoardVoltageFellBelowTheFatalAlarmThreshold	(132696),
			-- 132699:  Different SFUs were installed in the same chassis
			differentSFUswereinstalledinthesamechassis	(132699),
			-- 132712:  The board voltage exceeded the major alarm threshold
			theBoardVoltageExceededTheMajorAlarmThreshold	(132712),
			-- 132713:  The board voltage fell below the major alarm threshold
			theBoardVoltageFellBelowTheMajorAlarmThreshold	(132713),
			-- 132714:  The SD5K communication failed
			theSd5kCommunicationFailed	(132714),
			-- 132721:  The device hardware verification failed
			deviceHardwareVerifyFail	(132721),
			-- 133120:  The Master/slave Board Switchover Was Performed
			theMasterSlaveBoardSwitchoverWasPerformed	(133120),
			-- 133121:  PMU Board Leave Master
			pMUBoardLeaveMaster	(133121),
			-- 133122:  PMU Board Become Master
			pMUBoardBecomeMaster	(133122),
			-- 133376:  The Subcard Was Removed
			theSubcardWasRemoved	(133376),
			-- 133377:  A Storage Medium Was Removed
			aStorageMediumWasRemoved	(133377),
			-- 133632:  PMU RTC Clock Fault
			pMURTCClockFault	(133632),
			-- 133633:  PMU Hardware Fault
			pMUHardwareFault	(133633),
			-- 133634:  PMU BUS Fault
			pMUBUSFault	(133634),
			-- 135168:  The Monitoring Channel Of The Subcard Was Faulty
			theMonitoringChannelOfTheSubcardWasFaulty	(135168),
			-- 135169:  The In-position Signal Of The Subcard Was Faulty
			theInPositionSignalOfTheSubcardWasFaulty	(135169),
			-- 135170:  The Sensor On The Subcard Was Faulty
			theSensorOnTheSubcardWasFaulty	(135170),
			-- 135171:  The Reset Signal Of The Subcard Was Faulty
			theResetSignalOfTheSubcardWasFaulty	(135171),
			-- 135172:  The PLL On The Sub-board Malfunctions
			thePLLOnTheSubBoardMalfunctions	(135172),
			-- 135173:  The Clock On The Sub-board Malfunctions
			theClockOnTheSubBoardMalfunctions	(135173),
			-- 135174:  The DSP On The Sub-board Malfunctions
			theDSPOnTheSubBoardMalfunctions	(135174),
			-- 135175:  The FE PHY Chip On The Sub-board Malfunctions
			theFEPHYChipOnTheSubBoardMalfunctions	(135175),
			-- 135176:  The GE PHY Chip On The Sub-board Malfunctions
			theGEPHYChipOnTheSubBoardMalfunctions	(135176),
			-- 135177:  Faults With The LLP Chip Of The Sub-board Malfunctions
			faultsWithTheLLPChipOfTheSubBoardMalfunctions	(135177),
			-- 135178:  The LIU On The Sub-board Malfunctions
			theLIUOnTheSubBoardMalfunctions	(135178),
			-- 135179:  The ASIC On The Sub-board Malfunctions
			theASICOnTheSubBoardMalfunctions	(135179),
			-- 135180:  The Chip On The Sub-board Malfunctions
			theChipOnTheSubBoardMalfunctions	(135180),
			-- 135182:  ASIC On The Sub-board Malfunctions
			aSICOnTheSubBoardMalfunctions	(135182),
			-- 135184:  The Interface Numbered 1 On The Subcard Is Reserved But Does Not Forward Traffic. If An Optical Module Is Installed On The Interface Numbered 1, The Alarm Is Generated
			theInterfaceNumbered1OnTheSubcardIsReservedButDoesNotForwardTraffic	(135184),
			-- 135185:  Optical Card CDR Fault
			opticalCardCDRFault	(135185),
			-- 135190:  Battery Power Of The Physical Interface Card Is Lower Than 20%
			batteryPowerOfThePhysicalInterfaceCardIsLowerThan20Percent	(135190),
			-- 135191:  Battery Temperature Of The Physical Interface Card Is Lower Than The Low Threshold
			batteryTemperatureOfThePhysicalInterfaceCardIsLowerThanTheLowThreshold	(135191),
			-- 135192:  Battery Of The Physical Interface Card Is Overheated At Discharging
			batteryOfThePhysicalInterfaceCardIsOverheatedAtDischarging	(135192),
			-- 135193:  Battery Of The Physical Interface Card Is Overheated At Recharging
			batteryOfThePhysicalInterfaceCardIsOverheatedAtRecharging	(135193),
			-- 135194:  IIC Bus Error
			iICBusError	(135194),
			-- 135195:  Interface MAC CRC Error On A Subcard
			interfaceMACCRCErrorOnASubcard	(135195),
			-- 135196:  E-label CRC Error On A Subcard
			e-labelCRCErrorOnASubcard	(135196),
			-- 135204:  Failed to check the voltage
			theVoltageFailedToBeChecked    (135204),
			-- 135424:  The EPLD Logic Of The Subcard Was Faulty
			theEPLDLogicOfTheSubcardWasFaulty	(135424),
			-- 135425:  The FPGA Logic Of The Subcard Was Faulty
			theFPGALogicOfTheSubcardWasFaulty	(135425),
			-- 135426:  The Key Chip On The Subcard Was Faulty
			theKeyChipOnTheSubcardWasFaulty	(135426),
			-- 135427:  The Clock Unit On The Subcard Was Faulty
			theClockUnitOnTheSubcardWasFaulty	(135427),
			-- 135428:  The Subcard Does Not Match The Slot
			theSubcardDoesNotMatchTheSlot	(135428),
			-- 135429:  The NP Of The Subcard Was Faulty
			theNPOfTheSubcardWasFaulty	(135429),
			-- 135430:  The Heartbeats On The Subcard Was Faulty
			theHeartbeatsOnTheSubcardWasFaulty	(135430),
			-- 135431:  The TM Chip On The Subcard Was Faulty
			theTMChipOnTheSubcardWasFaulty	(135431),
			-- 135432:  Subcard Registration Failed
			subcardRegistrationFailed	(135432),
			-- 135433:  The Storage Chip On The Subcard Was Faulty
			theStorageChipOnTheSubcardWasFaulty	(135433),
			-- 135434:  The Data Channel Of The Subcard Was Faulty
			theDataChannelOfTheSubcardWasFaulty	(135434),
			-- 135435:  The Subcard Did Not Match The Slot
			theSubcardDidNotMatchTheSlot	(135435),
			-- 135436:  Back Clock On The Sub-board Malfunctions
			backClockOnTheSubBoardMalfunctions	(135436),
			-- 135437:  The Control Logic On The Sub-board Malfunctions
			theControlLogicOnTheSubBoardMalfunctions	(135437),
			-- 135438:  The Service Logic On The Sub-board Malfunctions
			theServiceLogicOnTheSubBoardMalfunctions	(135438),
			-- 135439:  The Card Was Powered Off
			theCardWasPoweredOff	(135439),
			-- 135440:  Optical Card Is Abnormal And Can Not Be Used
			opticalCardIsAbnormalAndCanNotBeUsed	(135440),
			-- 135441:  Subcard Registration Failed Due To User Configuration
			subcardRegistrationFailedDueToUserConfiguration	(135441),
			-- 135442:  The Card Is Incompatible With System Software
			theCardIsIncompatibleWithSystemSoftware	(135442),
			-- 135443:  Card Exceeds Limit Of Current
			cardExceedsLimitOfCurrent	(135443),
			-- 135444:  The Physical Interface Card Secondary Control Bus Error
			thePhysicalInterfaceCardSecondaryControlBusError	(135444),
			-- 135445:  The Physical Interface Card Power Off Due To Overheating
			thePhysicalInterfaceCardPowerOffDueToOverheating	(135445),
			-- 135446:  FSU Physical Interface Card Power Off
			fSUPhysicalInterfaceCardPowerOff	(135446),
			-- 135447:  The Slave Data Channel Of The Subcard Was Faulty
			theSlaveDataChannelOfTheSubcardWasFaulty	(135447),
			-- 135448:  The Slave Keychip Of The Subcard Was Faulty
			theSlaveKeychipOfTheSubcardWasFaulty	(135448),
			-- 135479:  Subcard Registration Failed Due To insufficient power
			subcardRegistrationFailedDueToInsufficientPower	(135479),
			-- 135680:  The Optical Module Was Removed
			theOpticalModuleWasRemoved	(135680),
			-- 135681:  The Optical Module Was Inserted
			theOpticalModuleWasInserted	(135681),
			-- 135936:  The Optical Module Did Not Match The Subcard
			theOpticalModuleDidNotMatchTheSubcard	(135936),
			-- 135937:  Optical Module Transmission Power Is Too High
			opticalModuleTransmissionPowerIsTooHigh	(135937),
			-- 135938:  Optical Module Transmission Power Is Too Low
			opticalModuleTransmissionPowerIsTooLow	(135938),
			-- 135939:  Optical Module Receiving Power Is Too High
			opticalModuleReceivingPowerIsTooHigh	(135939),
			-- 135940:  Optical Module Receiving Power Is Too Low
			opticalModuleReceivingPowerIsTooLow	(135940),
			-- 135941:  Optical Module Voltage Is Too High
			opticalModuleVoltageIsTooHigh	(135941),
			-- 135942:  Optical Module Voltage Is Too Low
			opticalModuleVoltageIsTooLow	(135942),
			-- 135943:  Optical Module Current Is Too High
			opticalModuleCurrentIsTooHigh	(135943),
			-- 135944:  Optical Module Current Is Too Low
			opticalModuleCurrentIsTooLow	(135944),
			-- 135945:  Optical Module Temperature Is Too High
			opticalModuleTemperatureIsTooHigh	(135945),
			-- 135946:  Optical Module Temperature Is Too Low
			opticalModuleTemperatureIsTooLow	(135946),
                        -- 135950:  PON Module No License
                        ponModuleNoLicense (135950),
			--135951: Some lanes of the optical module are faulty
			SomeLanesOfTheOpticalModuleAreFaulty     (135951),
			-- 136192:  The Optical Module Worked Abnormally
			theOpticalModuleWorkedAbnormally	(136192),
			-- 136193:  The Output Optical Power Was Too High
			theOutputOpticalPowerWasTooHigh	(136193),
			-- 136194:  The Output Optical Power Of The Optical Module Was Too Low
			theOutputOpticalPowerOfTheOpticalModuleWasTooLow	(136194),
			-- 136195:  The Input Optical Power Was Too High
			theInputOpticalPowerWasTooHigh	(136195),
			-- 136196:  The Input Optical Power Was Too Low
			theInputOpticalPowerWasTooLow	(136196),
			-- 136197:  The Voltage Of The Optical Module Was Too High
			theVoltageOfTheOpticalModuleWasTooHigh	(136197),
			-- 136198:  The Voltage Of The Optical Module Was Too Low
			theVoltageOfTheOpticalModuleWasTooLow	(136198),
			-- 136199:  The Bias Current Of The Optical Module Was Too High
			theBiasCurrentOfTheOpticalModuleWasTooHigh	(136199),
			-- 136200:  The Bias Current Of The Optical Module Was Too Low
			theBiasCurrentOfTheOpticalModuleWasTooLow	(136200),
			-- 136201:  The Temperature Of The Optical Module Was Too High
			theTemperatureOfTheOpticalModuleWasTooHigh	(136201),
			-- 136202:  The Temperature Of The Optical Module Was Too Low
			theTemperatureOfTheOpticalModuleWasTooLow	(136202),
			-- 136203:  Optical Model Dismatch
			opticalModelDismatch	(136203),
			-- 136204:  The Service Life Of The Optical Module Laser Is About To Expire
			theServiceLifeOfTheOpticalModuleLaserIsAboutToExpire	(136204),
			-- 136205:  PLD Or Flash Initialization Failed
			pLDOrFlashInitializationFailed	(136205),
			-- 136206:  Optical Module Power Supply Error
			opticalModulePowerSupplyError	(136206),
			-- 136207:  CFP Checksum Error
			cFPChecksumError	(136207),
			-- 136242:  The power current of the optical module is too high
			thePowerCurrentOfTheOpticalModuleIsTooHigh	(136242),
			-- 136247: The optical module was abnormal
			TheOpticalModuleWasAbnormal     (136247),
			-- 136254: Failed to configure wavelengths for the optical module
			FailedToConfigureWavelengthsForTheOpticalModule     (136254),
			-- 136255: The cable length of the medium does not match the port
			theCableLengthOfTheMediumDoesNotMatchThePort	(136255),
			-- 136256: The optical module fault on the host side
			TheOpticalModuleFaultOnTheHostSide     (136256),
			-- 136257: The optical module fault on the media side
			TheOpticalModuleFaultOnTheMediaSide     (136257),
			-- 136259: The temperature of the optical module laser was too high
			TheTemperatureOfTheOpticalModuleLaserWasTooHigh     (136259),
			-- 136260: The temperature of the optical module laser was too low
			TheTemperatureOfTheOpticalModuleLaserWasTooLow     (136260),
			-- 136261: The TEC current of the optical module laser was too high
			TheTecCurrentOfTheOpticalModuleLaserWasTooHigh     (136261),
			-- 136262: The TEC current of the optical module laser was too low
			TheTecCurrentOfTheOpticalModuleLaserWasTooLow     (136262),
			-- 136263: The receiving total power of the optical module was too high
			TheReceivingTotalPowerOfTheOpticalModuleWasTooHigh     (136263),
			-- 136264: The receiving total power of the optical module was too low
			TheReceivingTotalPowerOfTheOpticalModuleWasTooLow     (136264),
			-- 136265: The service life of the optical module laser was about to expire
			TheServiceLifeOfTheOpticalModuleLaserWasAboutToExpire     (136265),
			-- 136448:  The Power Supply Module Was Removed
			thePowerSupplyModuleWasRemoved	(136448),
			-- 136704:  Communication Between Power Supply Module And Device Failed
			communicationBetweenPowerSupplyModuleAndDeviceFailed	(136704),
			-- 136705:  Fans For Cooling The Power Supply Module Failed
			fansForCoolingThePowerSupplyModuleFailed	(136705),
			-- 136706:  The Lightning Protection Component Of The Power Supply Module Failed
			theLightningProtectionComponentOfThePowerSupplyModuleFailed	(136706),
			-- 136707:  The Power Supply Module Experienced A Partial Failure
			thePowerSupplyModuleExperiencedAPartialFailure	(136707),
			-- 136708:  The Electrically Erasable Programmable Read-only Memory (EEPROM) Of The Power Supply Module Failed
			theElectricallyErasableProgrammableReadOnlyMemoryEEPROMOfThePowerSupplyModuleFailed	(136708),
			-- 136709:  The Lightning Protection Component Of The Power Supply Module Failed(1+1-)
			theLightningProtectionComponentOfThePowerSupplyModuleFailed11		(136709),
			-- 136710:  The Lightning Protection Component Of The Power Supply Module Failed(2+2-)
			theLightningProtectionComponentOfThePowerSupplyModuleFailed22		(136710),
			-- 136711:  The Power Distribution Box Is Fail
			thePowerDistributionBoxIsFail	(136711),
			-- 136712:  Power Average Current Fault
			powerAverageCurrentFault	(136712),
			-- 136713:  The Port Expander Chip On The Power Module Failed
			thePortExpanderChipOnThePowerModuleFailed	(136713),
			-- 136714:  PM Average Current Fault
			pMAverageCurrentFault	(136714),
			-- 136715:  PM Bus Fault
			pMBusFault	(136715),
			-- 136716:  PM Current-limiting Fault
			pMCurrentLimitingFault	(136716),
			-- 136717:  PM Fault
			pMFault	(136717),
			-- 136718:  Power Back Board Absent
			powerBackBoardAbsent	(136718),
			-- 136719:  PM Module Single Channel Power Off
			pMModuleSingleChannelPowerOff	(136719),
			-- 136720:  Power Switch Error
			powerSwitchError	(136720),
			-- 136721:  BBU Loses The Input Power
			bBULosesTheInputPower	(136721),
			-- 136722:  BBU Power Supply Out Of Service
			bBUPowerSupplyOutOfService	(136722),
			-- 136723:  BBU Battery Out Of Service
			bBUBatteryOutOfService	(136723),
			-- 136724:  AC Power Abnormal
			aCPowerAbnormal	(136724),
			-- 136725:  Power Supply Module Chipset Failure
			powerSupplyModuleChipsetFailure	(136725),
			-- 136726:  Unknown Hardware Type Of A Power Board
			unknownHardwareTypeOfAPowerBoard	(136726),
			-- 136733:  The fan inside a power module fails
			thefaninsideapowermodulefails	(136733),
			-- 136960:  The Power Supply Module Was Not In Position
			thePowerSupplyModuleWasNotInPosition	(136960),
			-- 136961:  The Power Supply Module Failed
			thePowerSupplyModuleFailed	(136961),
			-- 136962:  The Input Voltage Of The Power Supply Module Was Higher Than The Maximum Voltage
			theInputVoltageOfThePowerSupplyModuleWasHigherThanTheMaximumVoltage	(136962),
			-- 136963:  The Input Voltage Of The Power Supply Module Was Lower Than The Minimum Voltage
			theInputVoltageOfThePowerSupplyModuleWasLowerThanTheMinimumVoltage	(136963),
			-- 136964:  The Temperature Of The Power Supply Module Was High
			theTemperatureOfThePowerSupplyModuleWasHigh	(136964),
			-- 136965:  The Input Fuse Of The AC Power Supply Module Was Disconnected
			theInputFuseOfTheACPowerSupplyModuleWasDisconnected	(136965),
			-- 136966:  The Power Supply Module Was Installed But Was Not Powered On
			thePowerSupplyModuleWasInstalledButWasNotPoweredOn	(136966),
			-- 136967:  The Output Of The Power Supply Module Failed
			theOutputOfThePowerSupplyModuleFailed	(136967),
			-- 136968:  The Output Voltage Of The Power Supply Module Was Higher Than The Maximum Voltage
			theOutputVoltageOfThePowerSupplyModuleWasHigherThanTheMaximumVoltage	(136968),
			-- 136969:  The Output Voltage Of The Power Supply Module Was Lower Than The Minimum Voltage
			theOutputVoltageOfThePowerSupplyModuleWasLowerThanTheMinimumVoltage	(136969),
			-- 136970:  The Power Supply Module Was Installed But Was Not Powered On(1+1-)
			thePowerSupplyModuleWasInstalledButWasNotPoweredOn11	(136970),
			-- 136971:  The Power Supply Module Was Installed But Was Not Powered On(2+2-)
			thePowerSupplyModuleWasInstalledButWasNotPoweredOn22	(136971),
			-- 136972:  POE Power Type Dismatch
			pOEPowerTypeDismatch	(136972),
			-- 136973:  Power Fault
			powerFault	(136973),
			-- 136974:  Power Of The Device Is Insufficient
			powerOfTheDeviceIsInsufficient	(136974),
			-- 136975:  The Device And The Power Module Did Not Match
			theDeviceAndThePowerModuleDidNotMatch	(136975),
			-- 136976:  The Alternating Power Supply Module Was Installed But Was Not Powered On
			theAlternatingPowerSupplyModuleWasInstalledButWasNotPoweredOn	(136976),
			-- 136977:  The Input Voltage Of The Power Supply Module Was Higher Than The Maximum Voltage(1+1-)
			theInputVoltageOfThePowerSupplyModuleWasHigherThanTheMaximumVoltage11	(136977),
			-- 136978:  The Input Voltage Of The Power Supply Module Was Lower Than The Minimum Voltage(1+1-)
			theInputVoltageOfThePowerSupplyModuleWasLowerThanTheMinimumVoltage11	(136978),
			-- 136979:  The Input Voltage Of The Power Supply Module Was Higher Than The Maximum Voltage(2+2-)
			theInputVoltageOfThePowerSupplyModuleWasHigherThanTheMaximumVoltage22	(136979),
			-- 136980:  The Input Voltage Of The Power Supply Module Was Lower Than The Minimum Voltage(2+2-)
			theInputVoltageOfThePowerSupplyModuleWasLowerThanTheMinimumVoltage22	(136980),
			-- 136981:  Output Power Exceeds The Rated Power
			outputPowerExceedsTheRatedPower	(136981),
			-- 136982:  A DC Power Is Inserted Into A AC Chassis Or A AC Power Is Inserted Into A DC Chassis
			aDCPowerIsInsertedIntoAACChassisOrAACPowerIsInsertedIntoADCChassis	(136982),
			-- 136983:  Power Supply Module Overheat Protection
			powerSupplyModuleOverheatProtection	(136983),
			-- 136984:  No Output Power Of RPS Power Supply
			noOutputPowerOfRPSPowerSupply	(136984),
			-- 136985:  Power Supply Module Is Installed In The Wrong Slot
			powerSupplyModuleIsInstalledInTheWrongSlot	(136985),
			-- 136996:  The wind direction of the power supply does not match the wind direction of the device
			powerSupplyWindDirecMisMatch	(136996),
			-- 137216:  The Fan Module Was Not Installed In The Slot
			theFanModuleWasNotInstalledInTheSlot	(137216),
			-- 137472:  The Fan Module Was In The Abnormal State
			theFanModuleWasInTheAbnormalState	(137472),
			-- 137473:  The Filter Board Dismatch The Frame
			theFilterBoardDismatchTheFrame	(137473),
			-- 137474:  Fan Wind Fault
			fanWindFault	(137474),
			-- 137475:  Fan Failure In Fan Module
			fanFailureInFanModule	(137475),
			-- 137728:  CMU Removed
			cMURemoved	(137728),
			-- 137888:  PMU Removed
			pMURemoved	(137888),
			-- 137984:  Optical Module Mismatch The Preconfiguration
			opticalModuleMismatchThePreconfiguration	(137984),
			-- 138240:  Ingress Traffic Is Too High On The Physical Interface Card
			ingressTrafficIsTooHighOnThePhysicalInterfaceCard	(138240),
			-- 138241:  Egress Traffic Is Too High On The Physical Interface Card
			egressTrafficIsTooHighOnThePhysicalInterfaceCard	(138241),
			-- 138253:  The bandwidth on the ILK system exceeds the threshold
	               theBandwidthOnTheILKSystemExceedsTheThreshold   (138253),
			-- 138400:  Port Removed
			portRemoved	(138400),
			-- 138416:  VNIC Resource Exceeds The Threshold
			vNICResourceExceedsTheThreshold	(138416),
			-- 139264:  The Hardware Of The Fan Module Was Faulty
			theHardwareOfTheFanModuleWasFaulty	(139264),
			-- 139265:  The Cable Of The Fan Module Was Disconnected
			theCableOfTheFanModuleWasDisconnected	(139265),
			-- 139266:  The Chassis And The Fan Module Did Not Match
			theChassisAndTheFanModuleDidNotMatch	(139266),
			-- 139267:  The 48 V Power Supply For The Fan Module Was Abnormal
			the48VPowerSupplyForTheFanModuleWasAbnormal	(139267),
			-- 139268:  The Fan Register Failed
			theFanRegisterFailed	(139268),
			-- 139269:  Failure Of Communication Between Fan And CMU
			failureOfCommunicationBetweenFanAndCMU	(139269),
			-- 139270:  Fan Absent
			fanAbsent	(139270),
			-- 139271:  Only One Fan Work Fault
			onlyOneFanWorkFault	(139271),
			-- 139520:  The LCD Was Not In Position
			theLCDWasNotInPosition	(139520),
			-- 139776:  The LCD Screen Was Detective
			theLCDScreenWasDetective	(139776),
			-- 139777:  A Piece Of Hardware Of The LCD Failed
			aPieceOfHardwareOfTheLCDFailed	(139777),
			-- 139778:  The LCD Cable Was Unconnected
			theLCDCableWasUnconnected	(139778),
			-- 139779:  The LCD Cable Was Unconnected But Services Would Not Be Affected
			theLCDCableWasUnconnectedButServicesWouldNotBeAffected	(139779),
			-- 140032:  The External Environment Became Abnormal
			theExternalEnvironmentBecameAbnormal	(140032),
			-- 140033:  Failure Of Communication Between MPU And CMU
			failureOfCommunicationBetweenMPUAndCMU	(140033),
			-- 140034:  CMUs Communication Failure
			cMUsCommunicationFailure	(140034),
			-- 140035:  CMU Hardware Fault
			cMUHardwareFault	(140035),
			-- 140036:  CMU Unregistered Fault
			cMUUnregisteredFault	(140036),
			-- 140288:  The Channel Monitoring Module Failed
			theChannelMonitoringModuleFailed	(140288),
			-- 140289:  A Data Channel Failed
			aDataChannelFailed	(140289),
			-- 140290:  Clock In Frame Failed
			clockInFrameFailed	(140290),
			-- 140291:  Data Bus Between Frame Failed
			dataBusBetweenFrameFailed	(140291),
			-- 140292:  Control Bus Between Frame Failed
			controlBusBetweenFrameFailed	(140292),
			-- 140304:  The I2C Control Bus On The Backplane Malfunctions
			theI2CControlBusOnTheBackplaneMalfunctions	(140304),
			-- 140305:  The I2C 1588 Clock Bus On The Backplane Malfunctions
			theI2C1588ClockBusOnTheBackplaneMalfunctions	(140305),
			-- 140306:  The GE Data Bus On The Backplane Malfunctions
			theGEDataBusOnTheBackplaneMalfunctions	(140306),
			-- 140307:  The System Clock Sent Through The Backplane Is Faulty
			theSystemClockSentThroughTheBackplaneIsFaulty	(140307),
			-- 140308:  The TOP Clock Sent Through The Backplane Is Faulty
			theTOPClockSentThroughTheBackplaneIsFaulty	(140308),
			-- 140309:  The 2K Frame Header Sent Through The Backplane Is Faulty
			the2KFrameHeaderSentThroughTheBackplaneIsFaulty	(140309),
			-- 140310:  ECM Chunnel Fault
			eCMChunnelFault	(140310),
			-- 140311:  The Serial Mangement Bus Of The Board Malfunctions
			theSerialMangementBusOfTheBoardMalfunctions	(140311),
			-- 140312:  CANBUS Fault
			cANBUSFault	(140312),
			-- 140313:  Loopback Control Channel Error
			loopbackControlChannelError	(140313),
			-- 140314:  IIC Bus To The Physical Interface Card Failure
			iICBusToThePhysicalInterfaceCardFailure	(140314),
			-- 140544:  The Ambient Temperature Was Too High
			theAmbientTemperatureWasTooHigh	(140544),
			-- 140545:  The Ambient Temperature Was Too Low
			theAmbientTemperatureWasTooLow	(140545),
			-- 140800:  The Ambient Humidity Was Too High
			theAmbientHumidityWasTooHigh	(140800),
			-- 140801:  The Ambient Humidity Was Too Low
			theAmbientHumidityWasTooLow	(140801),
			-- 141056:  The Out Voltage Is Too High
			theOutVoltageIsTooHigh	(141056),
			-- 141057:  The Out Voltage Is Too Low
			theOutVoltageIsTooLow	(141057),
			-- 141312:  Access Control Alarm
			accessControlAlarm	(141312),
			-- 141568:  Smoke Detection Alarm
			smokeDetectionAlarm	(141568),
			-- 143360:  The Board Was Improperly Installed
			theBoardWasImproperlyInstalled	(143360),
			-- 143361:  A Subcard Was Not Installed Securely
			aSubcardWasNotInstalledSecurely	(143361),
			-- 143616:  The Subcard Temperature Was Too High
			theSubcardTemperatureWasTooHigh	(143616),
			-- 143617:  The Board Temperature Was Too High
			theBoardTemperatureWasTooHigh	(143617),
			-- 143618:  The Fan Temperature Was Too High
			theFanTemperatureWasTooHigh	(143618),
			-- 143619:  Tempreture Is Lower Than Threhold
			tempretureIsLowerThanThrehold	(143619),
			-- 143620:  The Subcard Temperature Fell Below The Lower Limit
			theSubcardTemperatureFellBelowTheLowerLimit	(143620),
			-- 143621:  The Fan Temperature Fell Below The Lower Limit
			theFanTemperatureFellBelowTheLowerLimit	(143621),
			-- 143622:  The Power Module Temperature Fell Below The Lower Limit
			thePowerModuleTemperatureFellBelowTheLowerLimit	(143622),
			-- 143623:  The Power Module Temperature Was Too High
			thePowerModuleTemperatureWasTooHigh	(143623),
			-- 143627:  The Board Temperature is higher than the upper threshold
			theBoardTemperatureIsHigherThanTheUpperThreshold	(143627),
			-- 143872:  The Board Temperature Exceeded The Fatal Limit
			theBoardTemperatureExceededTheFatalLimit	(143872),
			-- 143873:  The Card Temperature Exceeded The Fatal Limit
			theCardTemperatureExceededTheFatalLimit	(143873),
			-- 143874:  The Fan Temperature Exceeded The Fatal Limit
			theFanTemperatureExceededTheFatalLimit	(143874),
			-- 143875:  Board Reboot Because Of Temperature Too High
			boardRebootBecauseOfTemperatureTooHigh	(143875),
			-- 143876:  The Power Module Temperature Was Extremely High
			thePowerModuleTemperatureWasExtremelyHigh	(143876),
			-- 144128:  The System Has No PAF Or License File, Or The PAF And License Files Are Invalid
			theSystemHasNoPAFOrLicenseFileOrThePAFAndLicenseFilesAreInvalid	(144128),
			-- 144129:  Board Dismatch SubSlot
			boardDismatchSubSlot	(144129),
			-- 144130:  The Software Package For Startup On The Slave MPU Was Inconsistent With That On The Master MPU Or The Software Package For Startup On The Master MPU Was Incomplete
			theSoftwarePackageForStartupOnTheSlaveMPUWasInconsistentWithTheMasterMPU	(144130),
			-- 144131:  The Slot For The Slave MPU Was Installed With An Unmatched Board
			theSlotForTheSlaveMPUWasInstalledWithAnUnmatchedBoard	(144131),
			-- 144132:  The Software Package For Startup In Really Mismatched That Been Set From Command Before Device Reboot
			theSoftwarePackageForStartupInReallyMismatchedThatBeenSetFromCommandBeforeDeviceReboot	(144132),
			-- 144133:  The Master And Slave MPUs' Memory Dismatch
			theMasterAndSlaveMPUsMemoryDismatch	(144133),
			-- 144134:  Device Type Dismatch The License File
			deviceTypeDismatchTheLicenseFile	(144134),
                        -- 144135:  The Master And Slave CFCARDs' Size Dismatch
                        theMasterAndSlaveCFCARDsSizeDismatch	(144135),
			-- 144384:  The Physical Interface Was Down
			thePhysicalInterfaceWasDown	(144384),
			-- 144896:  CPU Utilization Exceeded The Prealarm Threshold
			cPUUtilizationExceededThePrealarmThreshold	(144896),
			-- 145152:  Memory Utilization Exceeded The Prealarm Threshold
			memoryUtilizationExceededThePrealarmThreshold	(145152),
			-- 145408:  Current Startup File Is Not Exist
			currentStartupFileIsNotExist	(145408),
			-- 145409:  Current Startup File CRC Error
			currentStartupFileCRCError	(145409),
			-- 145410:  System Startup With Current Startup File Failed Times Than Threhold
			systemStartupWithCurrentStartupFileFailedTimesThanThrehold	(145410),
			-- 145664:  Storage Remove
			storageRemove	(145664),
			-- 145920:  The Optical Module Unauthorized
			theOpticalModuleUnauthorized	(145920),
			-- 146688:  There Is A FAN That Is Abnormal In The Fan Module
			thereIsAFANThatIsAbnormalInTheFanModule	(146688),
			-- 147208:  The CPU failed to send packets
			theCPUfailedtosendpackets	(147208),
			-- 147217:  Frequent erase and write operations are performed on the disk
			frequentEraseAndWriteOperationsArePerformedOnTheDisk	(147217),
			-- 147218:  The disk will soon become invalid
			thediskWillSoonBecomeInvalid	(147218),
			-- 147221:  The data disk will soon become invalid
			theDataDiskWillSoonBecomeInvalid	(147221),
			-- 155904:  The forwarding register was unstable
			theForwardingRegisterWasUnstable	(155904),
			-- 155648:  The coprocessor failed
			theCoprocessorFailed	          (155648),
                                                          -- 155649:  The PCIE interface of the forwarding chip failed
			pcieInterFault	          (155649),
			-- 155650:  The Die connectivity of the forwarding chip was abnormal
			dieCrackConnectionAbnormal	          (155650),
			-- 136222:  The TX FAULT of the optical module failed
			theTXFAULTOfTheOpticalModuleFailed              (136222),
			-- 143624:  Hard disk power supply voltage is abnormal
			hardDiskPowerSupplyVoltageIsAbnormal	          (143624),
			-- 75315:  Chip cascade port is abnormal
			chipCascadePortIsAbnormal	          (75315),
			-- 132143:  Voltage fault in the tested CPLD
			voltageFaultInTheTestedCPLD	          (132143),
			-- 132132:  clock 100 MHz fault
			clock100MHzFault	          (132132),
	                -- 136223:  The RX LOS of the optical module failed
  	               theRXLOSOfTheOpticalModuleFailed              (136223),
			-- 136233:  The speed of the optical module is mismatch with port
			theSpeedOfTheOpticalModuleIsMismatchWithPort	          (136233),
			-- 136234:  The optical was not certificated by HUAWEI
			theOpticalWasNotCertificatedByHUAWEI	          (136234),
			-- 132300:  Storage media is abnormal
			storageMediaAbnormal	          (132300),
			-- 132302:  The currently used hard disk is not certified by Huawei
			hardDiskIsNotCertifiedbyHuawei	          (132302),
			-- 132303:  The disk was pulled out
			diskPulledOut	          (132303),
                        -- 132372:  The board ha status is abnormal
			boardHaStatusIsAbnormal     (132372),
                        -- 155905:  The forwarding pipe is faulty
                        TheForwardingPipeIsFaulty	       (155905),
			-- 155906:  A data channel fault occured between forwarding chip and SFU
            ADataChannelFaultOccuredBetweenForwardingChipAndSfu	       (155906),
                        -- 155907:  Internal fatal fault of the forwarding chip
                        internalFatalFaultOfTheForwardingChip	       (155907),
			-- 155908:  Forwarding chip configuration error
                        forwardingChipConfigurationError	       (155908),
			-- 155909:  Forwarding chip fault caused by a device-side fault
                        forwardingChipFaultCausedByADeviceSideFault	       (155909),
                        -- 155910:  Self-healing memory fault of the forwarding chip
                        selfHealingMemoryFaultOfTheForwardingChip	       (155910),
			-- 155911:  Non-forwarding module fault of the forwarding chip
                        nonForwardingModuleFaultOfTheForwardingChip	       (155911),
			-- 155912:  Port failure on the forwarding chip
                        portFailureOnTheForwardingChip	       (155912),
			-- 155913:  Unstable port fault on the forwarding chip
                        unstablePortFaultOnTheForwardingChip	       (155913),
			-- 155914:  Invalid packet fault on the port of the forwarding chip
                        invalidPacketFaultOnThePortOfTheForwardingChip	       (155914)
	            }

	
--  Node definitions
-- 
-- Node definitions
-- 
-- 1.3.6.1.4.1.2011.5.25.219.1
		-- 1.3.6.1.4.1.2011.5.25.219.1
		hwEntityTrapObject OBJECT IDENTIFIER ::= { hwEntityTrapMIB 1 }

		
--  1.3.6.1.4.1.2011.5.25.219.1.1
		-- 1.3.6.1.4.1.2011.5.25.219.1.1
		hwEntityPhysicalIndex OBJECT-TYPE
			SYNTAX Integer32
			MAX-ACCESS read-write
			STATUS current
			DESCRIPTION
				"The index of physical."
			::= { hwEntityTrapObject 1 }

		
--  1.3.6.1.4.1.2011.5.25.219.1.2
		-- 1.3.6.1.4.1.2011.5.25.219.1.2
		hwEntityTrapEntType OBJECT-TYPE
			SYNTAX INTEGER
				{
				mpu(1),
				lpu(2),
				sfu(3),
				pic(4),
				cfcard(5),
				ofc(6),
				board(7),
				other(255)
				}
			MAX-ACCESS read-write
			STATUS current
			DESCRIPTION
				"The entity type."
			::= { hwEntityTrapObject 2 }

		
--  1.3.6.1.4.1.2011.5.25.219.1.3
		-- 1.3.6.1.4.1.2011.5.25.219.1.3
		hwEntityTrapFaultID OBJECT-TYPE
			SYNTAX HWTrapProbableCause
			MAX-ACCESS accessible-for-notify
			STATUS current
			DESCRIPTION
				"To describe the fault id of trap."
			::= { hwEntityTrapObject 3 }

		
--  1.3.6.1.4.1.2011.5.25.219.1.4
		-- 1.3.6.1.4.1.2011.5.25.219.1.4
		hwEntityCommunicateType OBJECT-TYPE
			SYNTAX INTEGER
				{
				controlChannel(1),
				monitorChannel(2),
				clockChannel(3),
				dataChannel(4)
				}
			MAX-ACCESS read-write
			STATUS current
			DESCRIPTION
				"The communicate type."
			::= { hwEntityTrapObject 4 }

		
--  1.3.6.1.4.1.2011.5.25.219.1.5
		-- 1.3.6.1.4.1.2011.5.25.219.1.5
		hwEntityThresholdTable OBJECT-TYPE
			SYNTAX SEQUENCE OF HwEntityThresholdEntry
			MAX-ACCESS not-accessible
			STATUS current
			DESCRIPTION
				"A table to config the threshold of each sensor."
			::= { hwEntityTrapObject 5 }

		
--  1.3.6.1.4.1.2011.5.25.219.1.5.1
		-- 1.3.6.1.4.1.2011.5.25.219.1.5.1
		hwEntityThresholdEntry OBJECT-TYPE
			SYNTAX HwEntityThresholdEntry
			MAX-ACCESS not-accessible
			STATUS current
			DESCRIPTION
				"The entry of threshold table."
			INDEX { entPhysicalIndex }
			::= { hwEntityThresholdTable 1 }

		
		HwEntityThresholdEntry ::=
			SEQUENCE { 
				hwEntityThresholdType
					INTEGER,
				hwEntityThresholdValue
					Integer32,
				hwEntityThresholdCurrent
					Integer32,
				hwEntityThresholdCritical
					Integer32,
				hwEntityThresholdWarning
					Integer32,
				hwEntityThresholdTip
					OCTET STRING
			 }

--  1.3.6.1.4.1.2011.5.25.219.1.5.1.1
		-- 1.3.6.1.4.1.2011.5.25.219.1.5.1.1
		hwEntityThresholdType OBJECT-TYPE
			SYNTAX INTEGER
				{
				riseOver(1),
				fallBelow(2)
				}
			MAX-ACCESS read-only
			STATUS current
			DESCRIPTION
				"The abnormal type for temperature, voltage, humidity......"
			::= { hwEntityThresholdEntry 1 }

		
--  1.3.6.1.4.1.2011.5.25.219.1.5.1.2
		-- 1.3.6.1.4.1.2011.5.25.219.1.5.1.2
		hwEntityThresholdValue OBJECT-TYPE
			SYNTAX Integer32
			MAX-ACCESS read-write
			STATUS current
			DESCRIPTION
				"The threshold value of temperature, humidity ,fog ......"
			::= { hwEntityThresholdEntry 2 }

		
--  1.3.6.1.4.1.2011.5.25.219.1.5.1.3
		-- 1.3.6.1.4.1.2011.5.25.219.1.5.1.3
		hwEntityThresholdCurrent OBJECT-TYPE
			SYNTAX Integer32
			MAX-ACCESS read-only
			STATUS current
			DESCRIPTION
				"The current value that been measured."
			::= { hwEntityThresholdEntry 3 }

		
--  1.3.6.1.4.1.2011.5.25.219.1.5.1.4
		-- 1.3.6.1.4.1.2011.5.25.219.1.5.1.4
		hwEntityThresholdCritical OBJECT-TYPE
			SYNTAX Integer32
			MAX-ACCESS read-write
			STATUS current
			DESCRIPTION
				"The critical alarm threshold for critical alarm. It could be used
				for a more dangerous instance than hwEntityThresholdCritical."
			::= { hwEntityThresholdEntry 4 }

		
--  1.3.6.1.4.1.2011.5.25.219.1.5.1.5
		-- 1.3.6.1.4.1.2011.5.25.219.1.5.1.5
		hwEntityThresholdWarning OBJECT-TYPE
			SYNTAX Integer32
			MAX-ACCESS read-write
			STATUS current
			DESCRIPTION
				"The warning alarm threshold for warning alarm. It could be used
				for a more dangerous instance than hwEntityThresholdWarning."
			::= { hwEntityThresholdEntry 5 }


--  1.3.6.1.4.1.2011.5.25.219.1.5.1.15
		-- 1.3.6.1.4.1.2011.5.25.219.1.5.1.15
		hwEntityThresholdTip OBJECT-TYPE
			SYNTAX OCTET STRING
			MAX-ACCESS read-write
			STATUS current
			DESCRIPTION
				"The tip to user."
			::= { hwEntityThresholdEntry 6 }


--  1.3.6.1.4.1.2011.5.25.219.1.5.1.6           
		-- 1.3.6.1.4.1.2011.5.25.219.1.6
		hwUserDefAlarmName OBJECT-TYPE
			SYNTAX OCTET STRING
			MAX-ACCESS read-only
			STATUS current
			DESCRIPTION
				"Description."
			::= { hwEntityTrapObject 6 }


--  1.3.6.1.4.1.2011.5.25.219.1.5.1.7
		-- 1.3.6.1.4.1.2011.5.25.219.1.7
		hwUserDefChannel OBJECT-TYPE
			SYNTAX Integer32
			MAX-ACCESS read-write
			STATUS current
			DESCRIPTION
				"Description."
			::= { hwEntityTrapObject 7 }


--  1.3.6.1.4.1.2011.5.25.219.1.5.1.8
		--  1.3.6.1.4.1.2011.5.25.219.1.5.1.8
		hwSoftwareVersion OBJECT-TYPE
			SYNTAX OCTET STRING
			MAX-ACCESS accessible-for-notify
			STATUS current
			DESCRIPTION
				"The version of software."
			::= { hwEntityTrapObject 8 }


--  1.3.6.1.4.1.2011.5.25.219.1.5.1.9
		--  1.3.6.1.4.1.2011.5.25.219.1.5.1.9
		hwStartupSoftwareFileName OBJECT-TYPE
			SYNTAX OCTET STRING
			MAX-ACCESS accessible-for-notify
			STATUS current
			DESCRIPTION
				"The name of software."
			::= { hwEntityTrapObject 9 }


--  1.3.6.1.4.1.2011.5.25.219.1.5.1.10
		--  1.3.6.1.4.1.2011.5.25.219.1.5.1.10
		hwStorageDevName OBJECT-TYPE
			SYNTAX OCTET STRING
			MAX-ACCESS accessible-for-notify
			STATUS current
			DESCRIPTION
				"Description."
			::= { hwEntityTrapObject 10 }
		
		
--  1.3.6.1.4.1.2011.5.25.219.1.5.1.11
		--  1.3.6.1.4.1.2011.5.25.219.1.5.1.11
		hwPortDownReason OBJECT-TYPE
			SYNTAX OCTET STRING
			MAX-ACCESS accessible-for-notify
			STATUS current
			DESCRIPTION
				"AUAIS: The RX detects administrative(A) unit(U) alarm(A) indication(I) signal(S).
                                                                       B1TCA: The RX detects b1(B1) threshold(T) crossing(C) alarm(A).
                                                                       B2TCA: The RX detects b2(B2) threshold(T) crossing(C) alarm(A).
                                                                       B3TCA: The RX detects b3(B3) threshold(T) crossing(C) alarm(A).
                                                                       LAIS: The RX detects line(L) alarm(A) indication(I) signal(S).
                                                                       LCD: The RX detects loss(L) of code-group(C) delineation(D).
                                                                       LOF: The RX detects loss(L) of(O) frame(F).
                                                                       LOM: The RX detects loss(L) of(O) multiframe(M).
                                                                       LOP: The RX detects loss(L) of(O) pointer(M).
                                                                       LOS: The RX detects loss(L) of(O) signal(S).
                                                                       LRDI: The RX detects line(L) remote(R) defect(D) indication(I).
                                                                       LREI: The RX detects line(L) remote(R) error(D) indication(I).
                                                                       OOF: The RX detects out(O) of(O) frame(F).
                                                                       PAIS: The RX detects path(P) alarm(A) indication(I) signal(S).
                                                                       PPLM: The RX detects path(P) payload(P) label(L) mismatch(M).
                                                                       PRDI: The RX detects path(P) remote(R) defect(D) indication(I).
                                                                       PREI: The RX detects path(P) remote(R) error(E) indication(I).
                                                                       PUNEQ: The RX detects path(P) unequipped(UNEQ).
                                                                       RDOOL: The RX detects receive(R) data(D) out(O) of(O) lock(L).
                                                                       RROOL: The RX detects receive(R) reference(R) out(O) of(O) lock(L).
                                                                       SD: The RX detects signal(S) degrade(D).
                                                                       SF: The RX detects signal(S) fail(F).
                                                                       TROOL: The TX detects transmit(T) reference(R) out(O) of(O) lock(L).
                                                                       WLINK: The RX detects pcs link has failed (wis mode).
                                                                       TRANSCEIVER_OFFLINE: The transceiver is not in position.
                                                                       TRANSCEIVER_FAIL: A hardware failure occurs when accessing the transceiver.
                                                                       TRANSCEIVER_MISMATCH: The transceiver does not match the port-mode.
                                                                       TRANSCEIVER_UNKNOWN: The transceiver is unknown type.
                                                                       PMA_LOS: The PMA(physical medium attachment) detects loss of signal.
                                                                       PMA_UNLOCK: The PMA(physical medium attachment) detects receive data out of lock.
                                                                       PCS_HIGHBER: The PCS(physical coding sublayer) enter High-BER status.
                                                                       PCS_UNLOCK: The PCS(physical coding sublayer) detects receive data out of lock.
                                                                       LOCAL_FAULT: The RX detects Local Fault signal.
                                                                       REMOTE_FAULT: The RX detects Remote Fault signal.
                                                                       NEGOTIATION_FAIL: Auto-negotiation is not successful.
                                                                       SOFT_FORCE_DOWN: The interface was DOWN triggered by a protocol module or was administratively shut down.
                                                                       GPON_ACTIVATE_FAIL: The GPON optical module failed to be detected or activated. 
                                                                       GPON_AUTHEN_LOID_FAIL: The authentication failed because the GPON optical module does not have an LOID. 
                                                                       GPON_AUTHEN_PASSWORD_FAIL: The authentication failed because the password is incorrect.
                                                                       GPON_AUTHEN_LOIDCOLLI_FAIL: The authentication failed due to LODI collision of GPON optical modules.
                                                                       GPON_FIBER_LINKFAULT_FAIL: The optical link failed due to link disconnection or low optical receive power.
                                                                       GPON_TRANSCEIVERSHUT_FAIL: The transmitter of the GPON optical module was turned off on the OLT.
                                                                       GPON_ABNORMALSHINE_FAIL: The GPON optical module detected light emitting abnormalities, and the transmitter was turned off.
                                                                       GPON_TRANSCEIVERABNORMAL: Laser is in fault state.
                                                                       GPON_OTHER_ALARM: The GPON optical module has other fault."
                                			::= { hwEntityTrapObject 11 }

--  1.3.6.1.4.1.2011.5.25.219.1.5.1.12
		--  1.3.6.1.4.1.2011.5.25.219.1.5.1.12
		hwEntityTrapRelativeResource OBJECT-TYPE
			SYNTAX MacAddress
			MAX-ACCESS accessible-for-notify
			STATUS current
			DESCRIPTION
				"MAC address."
			::= { hwEntityTrapObject 12 }
			
--  1.3.6.1.4.1.2011.5.25.219.1.5.1.13
		--  1.3.6.1.4.1.2011.5.25.219.1.5.1.13
		hwEntityTrapReasonDescr OBJECT-TYPE
			SYNTAX OCTET STRING
			MAX-ACCESS accessible-for-notify
			STATUS current
			DESCRIPTION
				"Description of trap reason."
			::= { hwEntityTrapObject 13 }		

--  1.3.6.1.4.1.2011.5.25.219.1.5.1.14
		-- 1.3.6.1.4.1.2011.5.25.219.1.5.1.14
		hwUsbOperType OBJECT-TYPE
			SYNTAX Integer32
			MAX-ACCESS read-write
			STATUS current
			DESCRIPTION
				"The staus of usb card."
			::= { hwEntityTrapObject 14 }
                
-- 1.3.6.1.4.1.2011.5.25.219.1.15
        -- 1.3.6.1.4.1.2011.5.25.219.1.15
		hwOpticalVendorName OBJECT-TYPE
			SYNTAX OCTET STRING
			MAX-ACCESS accessible-for-notify
			STATUS current
			DESCRIPTION
				"The vendor name of optical module."
			::= { hwEntityTrapObject 15 }
		
		-- 1.3.6.1.4.1.2011.5.25.219.1.16
		hwOpticalVendorSN OBJECT-TYPE
			SYNTAX OCTET STRING
			MAX-ACCESS accessible-for-notify
			STATUS current
			DESCRIPTION
				"The vendor serial number of optical module."
			::= { hwEntityTrapObject 16 }

-- 1.3.6.1.4.1.2011.5.25.219.1.17
        -- 1.3.6.1.4.1.2011.5.25.219.1.17
		hwMasterOpUser OBJECT-TYPE
			SYNTAX OCTET STRING
			MAX-ACCESS accessible-for-notify
			STATUS current
			DESCRIPTION
				"The master user name of virtual-access configuration."
			::= { hwEntityTrapObject 17 }
			
-- 1.3.6.1.4.1.2011.5.25.219.1.18
        -- 1.3.6.1.4.1.2011.5.25.219.1.18
		hwAPAdminIP OBJECT-TYPE
			SYNTAX OCTET STRING
			MAX-ACCESS accessible-for-notify
			STATUS current
			DESCRIPTION
				"The AP admin ip address of virtual-access configuration."
			::= { hwEntityTrapObject 18 }
			
-- 1.3.6.1.4.1.2011.5.25.219.1.19
        -- 1.3.6.1.4.1.2011.5.25.219.1.19
		hwAPID OBJECT-TYPE
			SYNTAX Integer32
			MAX-ACCESS accessible-for-notify
			STATUS current
			DESCRIPTION
				"The ap-id of virtual-access configuration."
			::= { hwEntityTrapObject 19 }

-- 1.3.6.1.4.1.2011.5.25.219.1.20
        -- 1.3.6.1.4.1.2011.5.25.219.1.20
		hwOperation OBJECT-TYPE
			SYNTAX OCTET STRING
			MAX-ACCESS accessible-for-notify
			STATUS current
			DESCRIPTION
				"The operation of virtual-access configuration."
			::= { hwEntityTrapObject 20 }
			
-- 1.3.6.1.4.1.2011.5.25.219.1.21
        -- 1.3.6.1.4.1.2011.5.25.219.1.21
		hwReason OBJECT-TYPE
			SYNTAX OCTET STRING
			MAX-ACCESS accessible-for-notify
			STATUS current
			DESCRIPTION
				"The failure reason of virtual-access configuration."
			::= { hwEntityTrapObject 21 }

-- 1.3.6.1.4.1.2011.5.25.219.1.23
        -- 1.3.6.1.4.1.2011.5.25.219.1.23
		vmName OBJECT-TYPE
			SYNTAX OCTET STRING
			MAX-ACCESS accessible-for-notify
			STATUS current
			DESCRIPTION
				"The name of VM."
			::= { hwEntityTrapObject 23 }
-- 1.3.6.1.4.1.2011.5.25.219.1.24
        -- 1.3.6.1.4.1.2011.5.25.219.1.24
		hwEntityBandwidthMode OBJECT-TYPE
                                                                  SYNTAX INTEGER {eth28x10gf(1),eth26x10gf18xgf(2),eth20x10gf24xgf(3),eth2x50ge2x25ge2x10gf14xgf(16),eth2x50ge6x10gf14xgf(17),eth2x25ge12x10gf14xgf(18),eth16x10gf14xgf(19)}
			MAX-ACCESS read-only
			STATUS current
			DESCRIPTION
				" The bandwidth mode of card."
			::= { hwEntityTrapObject 24 }

		-- 1.3.6.1.4.1.2011.5.25.219.1.25
		hwPartitionTable OBJECT-TYPE
			SYNTAX SEQUENCE OF HwPartitionEntry
			MAX-ACCESS not-accessible
			STATUS current
			DESCRIPTION
				"This table describes disk partition information. Currently, it is only used for disk partition-related alarms.
Creation Restriction: No entry can be created in this table.
Modification Restriction: The entries in this table cannot be modified.
Deletion Restriction: The entries in this table cannot be deleted.
Access Restriction: The entries in this table cannot be accessed."
			::= { hwEntityTrapObject 25 }

		
--  1.3.6.1.4.1.2011.5.25.219.1.25.1
		-- 1.3.6.1.4.1.2011.5.25.219.1.25.1
		hwPartitionEntry OBJECT-TYPE
			SYNTAX HwPartitionEntry
			MAX-ACCESS not-accessible
			STATUS current
			DESCRIPTION
				"A device disk partition entry. Each entry consists of information of a device disk partition.
                                                                              hwPartitionEntPhysicalName and hwPartitionName exclusively decide a device disk partition."
			INDEX { hwPartitionEntPhysicalName, hwPartitionName}
			::= { hwPartitionTable 1 }

		
		HwPartitionEntry ::=
			SEQUENCE { 
				hwPartitionEntPhysicalName
					OCTET STRING,
				hwPartitionName
					OCTET STRING,
				hwPartitionSpaceFree
					Integer32,
				hwPartitionSpaceFreeThreshold
					Integer32,
				hwPartitionUseage
					Integer32,
				hwPartitionUseageThreshold
					Integer32,
                                                                             hwEntPhysicalUbiIndex
					Integer32,
                                                                            hwEntCurrentBadPhysicalBlocks
					Integer32,
			                  hwEntBadPhysicalBlocksThreshold
					Integer32,
			                  hwEntMaxErasePhysicalBlocks
					Integer32,
			                  hwEntErasePhysicalBlocksThreshold
					Integer32

			 }


		hwPartitionEntPhysicalName OBJECT-TYPE
			SYNTAX OCTET STRING
			MAX-ACCESS accessible-for-notify
			STATUS current
			DESCRIPTION
				"This object indicates an entity name. "
			::= { hwPartitionEntry 1 }
			
			hwPartitionName OBJECT-TYPE
			SYNTAX OCTET STRING
			MAX-ACCESS accessible-for-notify
			STATUS current
			DESCRIPTION
				"This object indicates a disk partition name."
			::= { hwPartitionEntry 2 }

		
		hwPartitionSpaceFree OBJECT-TYPE
			SYNTAX Integer32
			MAX-ACCESS accessible-for-notify
			STATUS current
			DESCRIPTION
				"This object indicates the remaining disk partition space for the user, in MB."
			::= { hwPartitionEntry 3 }
		
		hwPartitionSpaceFreeThreshold OBJECT-TYPE
			SYNTAX Integer32
			MAX-ACCESS accessible-for-notify
			STATUS current
			DESCRIPTION
				"This object indicates the threshold for the remaining disk partition space for the user, in MB."
			::= { hwPartitionEntry 4 }
			
		hwPartitionUseage OBJECT-TYPE
			SYNTAX Integer32
			MAX-ACCESS accessible-for-notify
			STATUS current
			DESCRIPTION
				"This object indicates the current disk partition usage, in percentage."
			::= { hwPartitionEntry 5 }
			
		hwPartitionUseageThreshold OBJECT-TYPE
			SYNTAX Integer32
			MAX-ACCESS accessible-for-notify
			STATUS current
			DESCRIPTION
				"This object indicates the threshold for the disk partition usage, in percentage."
			::= { hwPartitionEntry 6 }
		
                                       hwEntPhysicalUbiIndex OBJECT-TYPE
			SYNTAX Integer32
			MAX-ACCESS accessible-for-notify
			STATUS current
			DESCRIPTION
				"This object indicates the current  physical ubi index number."
			::= { hwPartitionEntry 7 }

                                      hwEntCurrentBadPhysicalBlocks OBJECT-TYPE
			SYNTAX Integer32
			MAX-ACCESS accessible-for-notify
			STATUS current
			DESCRIPTION
				"This object indicates the current bad physical blocks number."
			::= { hwPartitionEntry 8 }

                                      hwEntBadPhysicalBlocksThreshold OBJECT-TYPE
			SYNTAX Integer32
			MAX-ACCESS accessible-for-notify
			STATUS current
			DESCRIPTION
				"This object indicates the threshold for the bad physical blocks number."
			::= { hwPartitionEntry 9 }
			
		hwEntMaxErasePhysicalBlocks OBJECT-TYPE
			SYNTAX Integer32
			MAX-ACCESS accessible-for-notify
			STATUS current
			DESCRIPTION
				"This object indicates the max erase physica blocks number."
			::= { hwPartitionEntry 10 }
			
		hwEntErasePhysicalBlocksThreshold OBJECT-TYPE
			SYNTAX Integer32
			MAX-ACCESS accessible-for-notify
			STATUS current
			DESCRIPTION
				"This object indicates the threshold for the max erase physical blocks number."
			::= { hwPartitionEntry 11 }
	
		--  1.3.6.1.4.1.2011.5.25.219.1.5.1.26
		hwEntPhysicalName  OBJECT-TYPE
			SYNTAX OCTET STRING
			MAX-ACCESS accessible-for-notify
			STATUS current
			DESCRIPTION
				"This object indicates an entity name. "
			::= { hwEntityTrapObject 26 }
		
		-- 1.3.6.1.4.1.2011.5.25.219.1.27
		hwBoardID OBJECT-TYPE
			SYNTAX Integer32
			MAX-ACCESS accessible-for-notify
			STATUS current
			DESCRIPTION
				"Board ID."
			::= { hwEntityTrapObject 27 }
		
-- 1.3.6.1.4.1.2011.5.25.219.1.28
        -- 1.3.6.1.4.1.2011.5.25.219.1.28
		hwPowerWorkMode OBJECT-TYPE
			SYNTAX OCTET STRING
			MAX-ACCESS accessible-for-notify
			STATUS current
			DESCRIPTION
				"AP power work mode."
			::= { hwEntityTrapObject 28 }
		
-- 1.3.6.1.4.1.2011.5.25.219.1.29
        -- 1.3.6.1.4.1.2011.5.25.219.1.29
		hwExpectPowerWorkMode OBJECT-TYPE
			SYNTAX OCTET STRING
			MAX-ACCESS accessible-for-notify
			STATUS current
			DESCRIPTION
				"AP excepted power work mode."
			::= { hwEntityTrapObject 29 }

-- 1.3.6.1.4.1.2011.5.25.219.1.30
        -- 1.3.6.1.4.1.2011.5.25.219.1.30
		hwCapCPUThresholdType OBJECT-TYPE
			SYNTAX Integer32
			MAX-ACCESS accessible-for-notify
			STATUS current
			DESCRIPTION
				"The type of changes of Cap CPU Utilization."
			::= { hwEntityTrapObject 30 }

-- 1.3.6.1.4.1.2011.5.25.219.1.31
        -- 1.3.6.1.4.1.2011.5.25.219.1.31
		hwCapCPUThresholdValue OBJECT-TYPE
			SYNTAX Integer32
			MAX-ACCESS accessible-for-notify
			STATUS current
			DESCRIPTION
				"The threshold value of Cap CPU Utilization."
			::= { hwEntityTrapObject 31 }

-- 1.3.6.1.4.1.2011.5.25.219.1.32
        -- 1.3.6.1.4.1.2011.5.25.219.1.32
		hwCapCPUThresholdCurrent OBJECT-TYPE
			SYNTAX Integer32
			MAX-ACCESS accessible-for-notify
			STATUS current
			DESCRIPTION
				"The average value of Cap CPU Utilization."
			::= { hwEntityTrapObject 32 }

-- 1.3.6.1.4.1.2011.5.25.219.1.33
		-- 1.3.6.1.4.1.2011.5.25.219.1.33
		hwSyslogModuleName OBJECT-TYPE
			SYNTAX OCTET STRING
			MAX-ACCESS accessible-for-notify
			STATUS current
			DESCRIPTION
				"The module name of syslog."
			::= { hwEntityTrapObject 33 }

		
-- 1.3.6.1.4.1.2011.5.25.219.1.34
		-- 1.3.6.1.4.1.2011.5.25.219.1.34
		hwSyslogSeverityLevel OBJECT-TYPE
			SYNTAX Integer32
			MAX-ACCESS accessible-for-notify
			STATUS current
			DESCRIPTION
				"The severity of syslog."
			::= { hwEntityTrapObject 34 }

		
-- 1.3.6.1.4.1.2011.5.25.219.1.35
		-- 1.3.6.1.4.1.2011.5.25.219.1.35
		hwSyslogBrief OBJECT-TYPE
			SYNTAX OCTET STRING
			MAX-ACCESS accessible-for-notify
			STATUS current
			DESCRIPTION
				"The brief of syslog."
			::= { hwEntityTrapObject 35 }

		
-- 1.3.6.1.4.1.2011.5.25.219.1.36
		-- 1.3.6.1.4.1.2011.5.25.219.1.36
		hwSyslogDescription OBJECT-TYPE
			SYNTAX OCTET STRING
			MAX-ACCESS accessible-for-notify
			STATUS current
			DESCRIPTION
				"The description of syslog."
			::= { hwEntityTrapObject 36 }

		
-- 1.3.6.1.4.1.2011.5.25.219.1.37
		-- 1.3.6.1.4.1.2011.5.25.219.1.37
		hwSyslogTimeStamp OBJECT-TYPE
			SYNTAX OCTET STRING
			MAX-ACCESS accessible-for-notify
			STATUS current
			DESCRIPTION
				"The time stamp of syslog."
			::= { hwEntityTrapObject 37 }

		-- 1.3.6.1.4.1.2011.5.25.219.1.38
		hwEntityNpsTrapObject OBJECT IDENTIFIER ::= { hwEntityTrapObject 38 }
		
		-- 1.3.6.1.4.1.2011.5.25.219.1.38.1
		hwEntityNpsVMName OBJECT-TYPE
			SYNTAX OCTET STRING
			MAX-ACCESS accessible-for-notify
			STATUS current
			DESCRIPTION
				"VM name."
			::= { hwEntityNpsTrapObject 1 }
		
		-- 1.3.6.1.4.1.2011.5.25.219.1.38.2
		hwEntityNpsVMID OBJECT-TYPE
			SYNTAX OCTET STRING
			MAX-ACCESS accessible-for-notify
			STATUS current
			DESCRIPTION
				"VMID of the MANO layer."
			::= { hwEntityNpsTrapObject 2 }
		
		-- 1.3.6.1.4.1.2011.5.25.219.1.38.3
		hwEntityNpsPhyVMID OBJECT-TYPE
			SYNTAX OCTET STRING
			MAX-ACCESS accessible-for-notify
			STATUS current
			DESCRIPTION
				"VMID of the physical layer."
			::= { hwEntityNpsTrapObject 3 }
		
		-- 1.3.6.1.4.1.2011.5.25.219.1.38.4
		hwEntityNpsErrorCode OBJECT-TYPE
			SYNTAX Integer32
			MAX-ACCESS accessible-for-notify
			STATUS current
			DESCRIPTION
				"The error code."
			::= { hwEntityNpsTrapObject 4 }
		
		-- 1.3.6.1.4.1.2011.5.25.219.1.38.5
		hwEntityNpsErrorDescr OBJECT-TYPE
			SYNTAX OCTET STRING
			MAX-ACCESS accessible-for-notify
			STATUS current
			DESCRIPTION
				"To describe the error of the trap."
			::= { hwEntityNpsTrapObject 5 }
		
		-- 1.3.6.1.4.1.2011.5.25.219.1.38.6
		hwEntityNpsPort OBJECT-TYPE
			SYNTAX Integer32
			MAX-ACCESS accessible-for-notify
			STATUS current
			DESCRIPTION
				"The port of the virtual machine."
			::= { hwEntityNpsTrapObject 6 }
		
		-- 1.3.6.1.4.1.2011.5.25.219.1.38.7
		hwEntityNpsPortName OBJECT-TYPE
			SYNTAX OCTET STRING
			MAX-ACCESS accessible-for-notify
			STATUS current
			DESCRIPTION
				"The port name of the virtual machine."
			::= { hwEntityNpsTrapObject 7 }
		
		-- 1.3.6.1.4.1.2011.5.25.219.1.38.8
		hwEntityNpsIPAddress OBJECT-TYPE
			SYNTAX OCTET STRING
			MAX-ACCESS accessible-for-notify
			STATUS current
			DESCRIPTION
				"The IP address of the virtual machine."
			::= { hwEntityNpsTrapObject 8 }
		
		-- 1.3.6.1.4.1.2011.5.25.219.1.38.9
		hwEntityNpsPatchName OBJECT-TYPE
			SYNTAX OCTET STRING
			MAX-ACCESS accessible-for-notify
			STATUS current
			DESCRIPTION
				"The patch file name."
			::= { hwEntityNpsTrapObject 9 }
		
		-- 1.3.6.1.4.1.2011.5.25.219.1.38.10
		hwEntityNpsPatchVersion OBJECT-TYPE
			SYNTAX OCTET STRING
			MAX-ACCESS accessible-for-notify
			STATUS current
			DESCRIPTION
				"The patch file version."
			::= { hwEntityNpsTrapObject 10 }
		
		-- 1.3.6.1.4.1.2011.5.25.219.1.38.11
		hwEntityNpsCertName OBJECT-TYPE
			SYNTAX OCTET STRING
			MAX-ACCESS accessible-for-notify
			STATUS current
			DESCRIPTION
				"The certificate file name."
			::= { hwEntityNpsTrapObject 11 }
		
		-- 1.3.6.1.4.1.2011.5.25.219.1.38.12
		hwEntityNpsCertType OBJECT-TYPE
			SYNTAX OCTET STRING
			MAX-ACCESS accessible-for-notify
			STATUS current
			DESCRIPTION
				"The certificate type."
			::= { hwEntityNpsTrapObject 12 }
		
		-- 1.3.6.1.4.1.2011.5.25.219.1.38.13
		hwEntityNpsCertRemainDays OBJECT-TYPE
			SYNTAX Integer32
			MAX-ACCESS accessible-for-notify
			STATUS current
			DESCRIPTION
				"The remain days of the certificate."
			::= { hwEntityNpsTrapObject 13 }
		
		-- 1.3.6.1.4.1.2011.5.25.219.1.38.14
		hwEntityNpsCertValidBeginTime OBJECT-TYPE
			SYNTAX OCTET STRING
			MAX-ACCESS accessible-for-notify
			STATUS current
			DESCRIPTION
				"The certificate valid begin time."
			::= { hwEntityNpsTrapObject 14 }
		
		-- 1.3.6.1.4.1.2011.5.25.219.1.38.15
		hwEntityNpsCertValidEndTime OBJECT-TYPE
			SYNTAX OCTET STRING
			MAX-ACCESS accessible-for-notify
			STATUS current
			DESCRIPTION
				"The certificate valid end time."
			::= { hwEntityNpsTrapObject 15 }
		
		-- 1.3.6.1.4.1.2011.5.25.219.1.38.16
		hwEntityNpsPartitionName OBJECT-TYPE
			SYNTAX OCTET STRING
			MAX-ACCESS accessible-for-notify
			STATUS current
			DESCRIPTION
				"The disk partition name."
			::= { hwEntityNpsTrapObject 16 }
		
		-- 1.3.6.1.4.1.2011.5.25.219.1.38.17
		hwEntityNpsPartitionUsage OBJECT-TYPE
			SYNTAX Integer32
			MAX-ACCESS accessible-for-notify
			STATUS current
			DESCRIPTION
				"The usage of the disk partition."
			::= { hwEntityNpsTrapObject 17 }
		
		-- 1.3.6.1.4.1.2011.5.25.219.1.38.18
		hwEntityNpsPartitionUsageThreshold OBJECT-TYPE
			SYNTAX Integer32
			MAX-ACCESS accessible-for-notify
			STATUS current
			DESCRIPTION
				"The disk partition usage overload threshold."
			::= { hwEntityNpsTrapObject 18 }
		
		-- 1.3.6.1.4.1.2011.5.25.219.1.38.19
		hwEntityNpsPartitionAvailableSpace OBJECT-TYPE
			SYNTAX Integer32
			MAX-ACCESS accessible-for-notify
			STATUS current
			DESCRIPTION
				"The available space of the disk partition."
			::= { hwEntityNpsTrapObject 19 }
		
		-- 1.3.6.1.4.1.2011.5.25.219.1.38.20
		hwEntityNpsPartitionCapacityThreshold OBJECT-TYPE
			SYNTAX Integer32
			MAX-ACCESS accessible-for-notify
			STATUS current
			DESCRIPTION
				"The capacity threshold of the disk partition."
			::= { hwEntityNpsTrapObject 20 }
		
		-- 1.3.6.1.4.1.2011.5.25.219.1.38.21
		hwEntityNpsRUName OBJECT-TYPE
			SYNTAX OCTET STRING
			MAX-ACCESS accessible-for-notify
			STATUS current
			DESCRIPTION
				"The name of RU."
			::= { hwEntityNpsTrapObject 21 }
		
		-- 1.3.6.1.4.1.2011.5.25.219.1.38.22
		hwEntityNpsVNFCName OBJECT-TYPE
			SYNTAX OCTET STRING
			MAX-ACCESS accessible-for-notify
			STATUS current
			DESCRIPTION
				"The name of the VNFC."
			::= { hwEntityNpsTrapObject 22 }
		
		-- 1.3.6.1.4.1.2011.5.25.219.1.38.23
		hwEntityNpsVNFCType OBJECT-TYPE
			SYNTAX OCTET STRING
			MAX-ACCESS accessible-for-notify
			STATUS current
			DESCRIPTION
				"The type of the VNFC."
			::= { hwEntityNpsTrapObject 23 }
		
		-- 1.3.6.1.4.1.2011.5.25.219.1.38.24
		hwEntityNpsAPPType OBJECT-TYPE
			SYNTAX OCTET STRING
			MAX-ACCESS accessible-for-notify
			STATUS current
			DESCRIPTION
				"The application type."
			::= { hwEntityNpsTrapObject 24 }
		
		-- 1.3.6.1.4.1.2011.5.25.219.1.38.25
		hwEntityNpsSoftwareVersionType OBJECT-TYPE
			SYNTAX OCTET STRING
			MAX-ACCESS accessible-for-notify
			STATUS current
			DESCRIPTION
				"The application version type."
			::= { hwEntityNpsTrapObject 25 }
		
		-- 1.3.6.1.4.1.2011.5.25.219.1.38.26
		hwEntityNpsSoftwareVersionID OBJECT-TYPE
			SYNTAX OCTET STRING
			MAX-ACCESS accessible-for-notify
			STATUS current
			DESCRIPTION
				"The application version id."
			::= { hwEntityNpsTrapObject 26 }
		
		-- 1.3.6.1.4.1.2011.5.25.219.1.38.27
		hwEntityNpsLocalVMName OBJECT-TYPE
			SYNTAX OCTET STRING
			MAX-ACCESS accessible-for-notify
			STATUS current
			DESCRIPTION
				"The local VM name."
			::= { hwEntityNpsTrapObject 27 }
		
		-- 1.3.6.1.4.1.2011.5.25.219.1.38.28
		hwEntityNpsRemoteVMName OBJECT-TYPE
			SYNTAX OCTET STRING
			MAX-ACCESS accessible-for-notify
			STATUS current
			DESCRIPTION
				"The remote VM name."
			::= { hwEntityNpsTrapObject 28 }
		
		-- 1.3.6.1.4.1.2011.5.25.219.1.38.29
		hwEntityNpsNetworkPlaneID OBJECT-TYPE
			SYNTAX Integer32
			MAX-ACCESS accessible-for-notify
			STATUS current
			DESCRIPTION
				"The network plane id."
			::= { hwEntityNpsTrapObject 29 }
		
		-- 1.3.6.1.4.1.2011.5.25.219.1.38.30
		hwEntityNpsNetworkErrorThreshold OBJECT-TYPE
			SYNTAX Integer32
			MAX-ACCESS accessible-for-notify
			STATUS current
			DESCRIPTION
				"The network subhealth threshold."
			::= { hwEntityNpsTrapObject 30 }
		
		-- 1.3.6.1.4.1.2011.5.25.219.1.38.31
		hwEntityNpsDeviceID OBJECT-TYPE
			SYNTAX OCTET STRING
			MAX-ACCESS accessible-for-notify
			STATUS current
			DESCRIPTION
				"The device id."
			::= { hwEntityNpsTrapObject 31 }
		
		-- 1.3.6.1.4.1.2011.5.25.219.1.38.32
		hwEntityNpsDriverVendor OBJECT-TYPE
			SYNTAX OCTET STRING
			MAX-ACCESS accessible-for-notify
			STATUS current
			DESCRIPTION
				"The driver vendor."
			::= { hwEntityNpsTrapObject 32 }
		
		-- 1.3.6.1.4.1.2011.5.25.219.1.38.33
		hwEntityNpsDriverType OBJECT-TYPE
			SYNTAX OCTET STRING
			MAX-ACCESS accessible-for-notify
			STATUS current
			DESCRIPTION
				"The driver type of device."
			::= { hwEntityNpsTrapObject 33 }
        --1.3.6.1.4.1.2011.5.25.219.1.38.34
		hwEntityNpsQuality OBJECT-TYPE
			SYNTAX Integer32
			MAX-ACCESS accessible-for-notify
			STATUS current
			DESCRIPTION
				"The quality of base."
			::= { hwEntityNpsTrapObject 34 }


                                   hwEntityConfigurationTrapObject OBJECT IDENTIFIER ::= { hwEntityTrapObject 39 }

                                    hwEntityConfigurationCurrent OBJECT-TYPE
			SYNTAX OCTET STRING
			MAX-ACCESS accessible-for-notify
			STATUS current
			DESCRIPTION
				"The current configuraiton."
			::= { hwEntityConfigurationTrapObject 1 }

                                    hwEntityConfigurationRollbackReason OBJECT-TYPE
			SYNTAX OCTET STRING
			MAX-ACCESS accessible-for-notify
			STATUS current
			DESCRIPTION
				"The configuration rollback reason."
			::= { hwEntityConfigurationTrapObject 2 }

-- 1.3.6.1.4.1.2011.5.25.219.1.40
		-- 1.3.6.1.4.1.2011.5.25.219.1.40
			hwLicenseRemainTime OBJECT-TYPE
			SYNTAX Integer32
			MAX-ACCESS accessible-for-notify
			STATUS current
			DESCRIPTION
				"The remain time of virtual license."
			::= { hwEntityTrapObject 40 }

-- 1.3.6.1.4.1.2011.5.25.219.1.41
			hwLpuSlotId OBJECT-TYPE
			SYNTAX OCTET STRING
			MAX-ACCESS accessible-for-notify
			STATUS current
			DESCRIPTION
				"The Id of the lpu board."
			::= { hwEntityTrapObject 41 }

-- 1.3.6.1.4.1.2011.5.25.219.1.42
			hwLpuFeId OBJECT-TYPE
			SYNTAX Integer32
			MAX-ACCESS accessible-for-notify
			STATUS current
			DESCRIPTION
				"Np id."
			::= { hwEntityTrapObject 42 }

-- 1.3.6.1.4.1.2011.5.25.219.1.43
			hwDropCauseId OBJECT-TYPE
			SYNTAX Integer32
			MAX-ACCESS accessible-for-notify
			STATUS current
			DESCRIPTION
				"The cause id of drop packet."
			::= { hwEntityTrapObject 43}

-- 1.3.6.1.4.1.2011.5.25.219.1.44
		-- 1.3.6.1.4.1.2011.5.25.219.1.44
		hwVirtualLicenseItemName OBJECT-TYPE
			SYNTAX OCTET STRING
			MAX-ACCESS accessible-for-notify
			STATUS current
			DESCRIPTION
				"The item name of virtual license."
			::= { hwEntityTrapObject 44 }

-- 1.3.6.1.4.1.2011.5.25.219.1.45
		-- 1.3.6.1.4.1.2011.5.25.219.1.45
		hwPorcessName OBJECT-TYPE
			SYNTAX OCTET STRING
			MAX-ACCESS accessible-for-notify
			STATUS current
			DESCRIPTION
				"The name of the process."
			::= { hwEntityTrapObject 45 }

-- 1.3.6.1.4.1.2011.5.25.219.1.46
		-- 1.3.6.1.4.1.2011.5.25.219.1.46
		hwInnerPortSlotId OBJECT-TYPE
			SYNTAX OCTET STRING
			MAX-ACCESS read-write
			STATUS current
			DESCRIPTION
				"The id of the slot."
			::= { hwEntityTrapObject 46 }
			
-- 1.3.6.1.4.1.2011.5.25.219.1.47
		-- 1.3.6.1.4.1.2011.5.25.219.1.47
		hwInnerPortCpuId OBJECT-TYPE
			SYNTAX Integer32
			MAX-ACCESS read-write
			STATUS current
			DESCRIPTION
				"The id of the cpu."
			::= { hwEntityTrapObject 47 }
			
-- 1.3.6.1.4.1.2011.5.25.219.1.48
		-- 1.3.6.1.4.1.2011.5.25.219.1.48
		hwInnerPortPortId OBJECT-TYPE
			SYNTAX Integer32
			MAX-ACCESS read-write
			STATUS current
			DESCRIPTION
				"The id of the port."
			::= { hwEntityTrapObject 48 }
			
-- 1.3.6.1.4.1.2011.5.25.219.1.49
        -- 1.3.6.1.4.1.2011.5.25.219.1.49
		hwContainerName OBJECT-TYPE
			SYNTAX OCTET STRING
			MAX-ACCESS accessible-for-notify
			STATUS current
			DESCRIPTION
				"The name of Container."
			::= { hwEntityTrapObject 49 }
			
-- 1.3.6.1.4.1.2011.5.25.219.1.50
        -- 1.3.6.1.4.1.2011.5.25.219.1.50
		hwContainerAppName OBJECT-TYPE
			SYNTAX OCTET STRING
			MAX-ACCESS accessible-for-notify
			STATUS current
			DESCRIPTION
				"The name of app run in Container."
			::= { hwEntityTrapObject 50 }

-- 1.3.6.1.4.1.2011.5.25.219.1.51
        -- 1.3.6.1.4.1.2011.5.25.219.1.51
		hwCapMemType OBJECT-TYPE
			SYNTAX OCTET STRING
			MAX-ACCESS accessible-for-notify
			STATUS current
			DESCRIPTION
				"The memory type of Cap memory Utilization."
			::= { hwEntityTrapObject 51 }
			
-- 1.3.6.1.4.1.2011.5.25.219.1.52
        -- 1.3.6.1.4.1.2011.5.25.219.1.52
		hwCapMemThresholdValue OBJECT-TYPE
			SYNTAX Integer32
			MAX-ACCESS accessible-for-notify
			STATUS current
			DESCRIPTION
				"The threshold value of Cap memory Utilization."
			::= { hwEntityTrapObject 52 }
			
-- 1.3.6.1.4.1.2011.5.25.219.1.53
        -- 1.3.6.1.4.1.2011.5.25.219.1.53
		hwCapMemThresholdCurrent OBJECT-TYPE
			SYNTAX Integer32
			MAX-ACCESS accessible-for-notify
			STATUS current
			DESCRIPTION
				"The average value of Cap memory Utilization."
			::= { hwEntityTrapObject 53 }

-- 1.3.6.1.4.1.2011.5.25.219.1.54
        -- 1.3.6.1.4.1.2011.5.25.219.1.54
		hwCapSingleCoreThresholdCurrent OBJECT-TYPE
			SYNTAX Integer32
			MAX-ACCESS accessible-for-notify
			STATUS current
			DESCRIPTION
				"The current value of Cap single core CPU Utilization."
			::= { hwEntityTrapObject 54 }

-- 1.3.6.1.4.1.2011.5.25.219.1.55
        -- 1.3.6.1.4.1.2011.5.25.219.1.55
		hwCapSingleCoreIndex OBJECT-TYPE
			SYNTAX Integer32
			MAX-ACCESS accessible-for-notify
			STATUS current
			DESCRIPTION
				"The core index of Cap single core CPU Utilization."
			::= { hwEntityTrapObject 55 }

-- 1.3.6.1.4.1.2011.5.25.219.1.56
        -- 1.3.6.1.4.1.2011.5.25.219.1.56
		hwCapSingleCoreThresholdValue OBJECT-TYPE
			SYNTAX Integer32
			MAX-ACCESS accessible-for-notify
			STATUS current
			DESCRIPTION
				"The threshold value of Cap single core CPU Utilization."
			::= { hwEntityTrapObject 56 }

-- 1.3.6.1.4.1.2011.5.25.219.1.57
        -- 1.3.6.1.4.1.2011.5.25.219.1.57
		hwEntityFrerLinkApID OBJECT-TYPE
			SYNTAX Integer32
			MAX-ACCESS accessible-for-notify
			STATUS current
			DESCRIPTION
				"The ApID of FRER Link."
			::= { hwEntityTrapObject 57 }

-- 1.3.6.1.4.1.2011.5.25.219.1.58
        -- 1.3.6.1.4.1.2011.5.25.219.1.58
		hwEntityFrerLinkWlanID OBJECT-TYPE
			SYNTAX Integer32
			MAX-ACCESS accessible-for-notify
			STATUS current
			DESCRIPTION
				"The WlanID of FRER Link."
			::= { hwEntityTrapObject 58 }

-- 1.3.6.1.4.1.2011.5.25.219.1.59
        -- 1.3.6.1.4.1.2011.5.25.219.1.59
		hwEntityFrerLinkRadioID OBJECT-TYPE
			SYNTAX Integer32
			MAX-ACCESS accessible-for-notify
			STATUS current
			DESCRIPTION
				"The RadioID of FRER Link."
			::= { hwEntityTrapObject 59 }
-- 1.3.6.1.4.1.2011.5.25.219.1.60
        -- 1.3.6.1.4.1.2011.5.25.219.1.60
		hwCapCurSipfpmFlowRate OBJECT-TYPE
			SYNTAX Integer32
			MAX-ACCESS accessible-for-notify
			STATUS current
			DESCRIPTION
				"Current Sipfpm flow rate."
			::= { hwEntityTrapObject 60 }
-- 1.3.6.1.4.1.2011.5.25.219.1.61
        -- 1.3.6.1.4.1.2011.5.25.219.1.61
		hwCapUpperSipfpmFlowThreshold OBJECT-TYPE
			SYNTAX Integer32
			MAX-ACCESS accessible-for-notify
			STATUS current
			DESCRIPTION
				"Upper alarm threshold of the Sipfpm flow rate."
			::= { hwEntityTrapObject 61 }
-- 1.3.6.1.4.1.2011.5.25.219.1.62
        -- 1.3.6.1.4.1.2011.5.25.219.1.62
		hwCapLowerSipfpmFlowThreshold OBJECT-TYPE
			SYNTAX Integer32
			MAX-ACCESS accessible-for-notify
			STATUS current
			DESCRIPTION
				"Lower alarm threshold of the Sipfpm flow rate."
			::= { hwEntityTrapObject 62 }

-- 1.3.6.1.4.1.2011.5.25.219.1.63
        -- 1.3.6.1.4.1.2011.5.25.219.1.63
		hwEntityCpeRemoteStationMAC OBJECT-TYPE
			SYNTAX MacAddress
			MAX-ACCESS accessible-for-notify
			STATUS current
			DESCRIPTION
				"Mac address of cpe remote station."
			::= { hwEntityTrapObject 63 }
			

--  1.3.6.1.4.1.2011.5.25.219.1.5.1.64          
		-- 1.3.6.1.4.1.2011.5.25.219.1.64
		hwDeviceMasterESN OBJECT-TYPE
			SYNTAX OCTET STRING
			MAX-ACCESS read-only
			STATUS current
			DESCRIPTION
				"ESN of the master device."
			::= { hwEntityTrapObject 64 }

        -- 1.3.6.1.4.1.2011.5.25.219.1.65
		hwCapCurSACSessionRate OBJECT-TYPE
			SYNTAX Integer32
			MAX-ACCESS accessible-for-notify
			STATUS current
			DESCRIPTION
				"Current SAC session rate."
			::= { hwEntityTrapObject 65 }
        -- 1.3.6.1.4.1.2011.5.25.219.1.66
		hwCapUpperSACSessionThreshold OBJECT-TYPE
			SYNTAX Integer32
			MAX-ACCESS accessible-for-notify
			STATUS current
			DESCRIPTION
				"Upper alarm threshold of the SAC session rate."
			::= { hwEntityTrapObject 66 }
        -- 1.3.6.1.4.1.2011.5.25.219.1.67
		hwCapLowerSACSessionThreshold OBJECT-TYPE
			SYNTAX Integer32
			MAX-ACCESS accessible-for-notify
			STATUS current
			DESCRIPTION
				"Lower alarm threshold of the SAC session rate."
			::= { hwEntityTrapObject 67 }

-- 1.3.6.1.4.1.2011.5.25.219.1.68
		--  1.3.6.1.4.1.2011.5.25.219.1.68
		hwHelpinfo OBJECT-TYPE
			SYNTAX OCTET STRING
			MAX-ACCESS accessible-for-notify
			STATUS current
			DESCRIPTION
				"Description of trap reason."
			::= { hwEntityTrapObject 68 }
			
-- 1.3.6.1.4.1.2011.5.25.219.1.69
		--  1.3.6.1.4.1.2011.5.25.219.1.69
		hwSlot OBJECT-TYPE
			SYNTAX Integer32
			MAX-ACCESS read-write
			STATUS current
			DESCRIPTION
				"Slot ID of the device."
			::= { hwEntityTrapObject 69 }
			
-- 1.3.6.1.4.1.2011.5.25.219.1.70
		--  1.3.6.1.4.1.2011.5.25.219.1.70
		hwLineId OBJECT-TYPE
			SYNTAX Integer32
			MAX-ACCESS read-write
			STATUS current
			DESCRIPTION
				"ID number of output line."
			::= { hwEntityTrapObject 70 }

			-- 1.3.6.1.4.1.2011.5.25.219.1.71
		hwAvailableMemory OBJECT-TYPE
			SYNTAX OCTET STRING
			MAX-ACCESS accessible-for-notify
			STATUS current
			DESCRIPTION
				"Available memory of system."
			::= { hwEntityTrapObject 71 }

		-- 1.3.6.1.4.1.2011.5.25.219.1.72
		hwAvailableMemoryThreshold OBJECT-TYPE
			SYNTAX OCTET STRING
			MAX-ACCESS accessible-for-notify
			STATUS current
			DESCRIPTION
				"Available memory threshold of system."
			::= { hwEntityTrapObject 72 }

-- 1.3.6.1.4.1.2011.5.25.219.1.73
        -- 1.3.6.1.4.1.2011.5.25.219.1.73
		hwEntityLossType OBJECT-TYPE
			SYNTAX OCTET STRING
			MAX-ACCESS accessible-for-notify
			STATUS current
			DESCRIPTION
				"The packet loss type."
			::= { hwEntityTrapObject 73 }
-- 1.3.6.1.4.1.2011.5.25.219.1.74
        -- 1.3.6.1.4.1.2011.5.25.219.1.74
		hwEntityLossCount OBJECT-TYPE
			SYNTAX OCTET STRING
			MAX-ACCESS accessible-for-notify
			STATUS current
			DESCRIPTION
				"The packet loss count."
			::= { hwEntityTrapObject 74 }
-- 1.3.6.1.4.1.2011.5.25.219.1.75
		--  1.3.6.1.4.1.2011.5.25.219.1.75
		hwEntityCoreIndex OBJECT-TYPE
			SYNTAX Integer32
			MAX-ACCESS accessible-for-notify
			STATUS current
			DESCRIPTION
				"The index of core that packet-loss alarm occured on."
			::= { hwEntityTrapObject 75 }	

-- 1.3.6.1.4.1.2011.5.25.219.1.76
		--  1.3.6.1.4.1.2011.5.25.219.1.76
		hwDeviceRebootTrapTime OBJECT-TYPE
			SYNTAX OCTET STRING
			MAX-ACCESS accessible-for-notify
			STATUS current
			DESCRIPTION
				"The device reboot time."
			::= { hwEntityTrapObject 76 }			

-- 1.3.6.1.4.1.2011.5.25.219.1.77
		--  1.3.6.1.4.1.2011.5.25.219.1.77
		hwDeviceRebootTrapReason OBJECT-TYPE
			SYNTAX OCTET STRING
			MAX-ACCESS accessible-for-notify
			STATUS current
			DESCRIPTION
				"The device reboot reason."
			::= { hwEntityTrapObject 77 }				
			
-- 1.3.6.1.4.1.2011.5.25.219.2
		-- 1.3.6.1.4.1.2011.5.25.219.2			
		hwEntityTraps OBJECT IDENTIFIER ::= { hwEntityTrapMIB 2 }	
		
--  1.3.6.1.4.1.2011.5.25.219.2.1
		-- 1.3.6.1.4.1.2011.5.25.219.2.1
		hwChassisTrap OBJECT IDENTIFIER ::= { hwEntityTraps 1 }

		
--  Frame has been removed.
-- 1.3.6.1.4.1.2011.5.25.219.2.1.1
		-- 1.3.6.1.4.1.2011.5.25.219.2.1.1
		hwChassisRemove NOTIFICATION-TYPE
			OBJECTS { hwEntityPhysicalIndex, entPhysicalName, hwEntityTrapFaultID, hwEntityOperStatus}
			STATUS current
			DESCRIPTION 
				"This object indicates that a chassis cannot be detected."
			::= { hwChassisTrap 1 }

		
--  1.3.6.1.4.1.2011.5.25.219.2.1.2
		-- 1.3.6.1.4.1.2011.5.25.219.2.1.2
		hwChassisInsert NOTIFICATION-TYPE
			OBJECTS { hwEntityPhysicalIndex, entPhysicalName, hwEntityTrapFaultID, hwEntityOperStatus}
			STATUS current
			DESCRIPTION 
				"This object indicates that a chassis can be detected."
			::= { hwChassisTrap 2 }

		
--  1.3.6.1.4.1.2011.5.25.219.2.1.3
		-- 1.3.6.1.4.1.2011.5.25.219.2.1.3
		hwChassisFail NOTIFICATION-TYPE
			OBJECTS { hwEntityPhysicalIndex, entPhysicalName, hwEntityTrapFaultID, hwEntityOperStatus, hwEntityTrapReasonDescr }
			STATUS current
			DESCRIPTION 
				"This object indicates that a chassis encounters a partial failure."
			::= { hwChassisTrap 3 }

		
--  1.3.6.1.4.1.2011.5.25.219.2.1.4
		-- 1.3.6.1.4.1.2011.5.25.219.2.1.4
		hwChassisFailResume NOTIFICATION-TYPE
			OBJECTS { hwEntityPhysicalIndex, entPhysicalName, hwEntityTrapFaultID, hwEntityOperStatus, hwEntityTrapReasonDescr }
			STATUS current
			DESCRIPTION 
				"This object indicates that a chassis recovers from a partial failure."
			::= { hwChassisTrap 4 }

		
--  1.3.6.1.4.1.2011.5.25.219.2.1.5
		-- 1.3.6.1.4.1.2011.5.25.219.2.1.5
		hwChassisInvalid NOTIFICATION-TYPE
			OBJECTS { hwEntityPhysicalIndex, entPhysicalName, hwEntityTrapFaultID, hwEntityOperStatus}
			STATUS current
			DESCRIPTION 
				"This object indicates that a chassis encounters an overall failure."
			::= { hwChassisTrap 5 }

		
--  1.3.6.1.4.1.2011.5.25.219.2.1.6
		-- 1.3.6.1.4.1.2011.5.25.219.2.1.6
		hwChassisInvalidResume NOTIFICATION-TYPE
			OBJECTS { hwEntityPhysicalIndex, entPhysicalName, hwEntityTrapFaultID, hwEntityOperStatus}
			STATUS current
			DESCRIPTION 
				"This object indicates that a chassis recovers from an overall failure."
			::= { hwChassisTrap 6 }

--  1.3.6.1.4.1.2011.5.25.219.2.1.7
		-- 1.3.6.1.4.1.2011.5.25.219.2.1.7
		hwChassisMinorAlarm NOTIFICATION-TYPE
			OBJECTS { hwEntityPhysicalIndex, entPhysicalName, hwEntityTrapFaultID }
			STATUS current
			DESCRIPTION 
				"This object indicates that a chassis encounters a minor failure."
			::= { hwChassisTrap 7 }

--  1.3.6.1.4.1.2011.5.25.219.2.1.8
		-- 1.3.6.1.4.1.2011.5.25.219.2.1.8
		hwChassisMinorAlarmResume NOTIFICATION-TYPE
			OBJECTS { hwEntityPhysicalIndex, entPhysicalName, hwEntityTrapFaultID }
			STATUS current
			DESCRIPTION 
				"This object indicates that a chassis recovers from a minor failure."
			::= { hwChassisTrap 8 }

--  1.3.6.1.4.1.2011.5.25.219.2.1.9
		-- 1.3.6.1.4.1.2011.5.25.219.2.1.9
		hwChassisPowerChanged NOTIFICATION-TYPE
			OBJECTS { entPhysicalIndex, entPhysicalName }
			STATUS current
			DESCRIPTION 
				"The power supply type of the chassis is changed."
			::= { hwChassisTrap 9 }

--  1.3.6.1.4.1.2011.5.25.219.2.2
		-- 1.3.6.1.4.1.2011.5.25.219.2.2
		hwBoardTrap OBJECT IDENTIFIER ::= { hwEntityTraps 2 }

		
--  1.3.6.1.4.1.2011.5.25.219.2.2.1
		-- 1.3.6.1.4.1.2011.5.25.219.2.2.1
		hwBoardRemove NOTIFICATION-TYPE
			OBJECTS { hwEntityPhysicalIndex, entPhysicalName, hwEntityTrapEntType, hwEntityTrapFaultID, hwEntityOperStatus}
			STATUS current
			DESCRIPTION 
				"This object indicates that a board cannot be detected."
			::= { hwBoardTrap 1 }

		
--  1.3.6.1.4.1.2011.5.25.219.2.2.2
		-- 1.3.6.1.4.1.2011.5.25.219.2.2.2
		hwBoardInsert NOTIFICATION-TYPE
			OBJECTS { hwEntityPhysicalIndex, entPhysicalName, hwEntityTrapEntType, hwEntityTrapFaultID, hwEntityOperStatus}
			STATUS current
			DESCRIPTION 
				"This object indicates that a board can be detected."
			::= { hwBoardTrap 2 }

		
--  1.3.6.1.4.1.2011.5.25.219.2.2.3
		-- 1.3.6.1.4.1.2011.5.25.219.2.2.3
		hwBoardFail NOTIFICATION-TYPE
			OBJECTS { hwEntityPhysicalIndex, entPhysicalName, hwEntityTrapEntType, hwEntityTrapFaultID, hwEntityTrapReasonDescr, hwEntityOperStatus}
			STATUS current
			DESCRIPTION 
				"This object indicates that a board encounters a partial failure."
			::= { hwBoardTrap 3 }

		
--  1.3.6.1.4.1.2011.5.25.219.2.2.4
		-- 1.3.6.1.4.1.2011.5.25.219.2.2.4
		hwBoardFailResume NOTIFICATION-TYPE
			OBJECTS { hwEntityPhysicalIndex, entPhysicalName, hwEntityTrapEntType, hwEntityTrapFaultID, hwEntityTrapReasonDescr, hwEntityOperStatus}
			STATUS current
			DESCRIPTION 
				"This object indicates that a board recovers from a partial failure."
			::= { hwBoardTrap 4 }

		
--  1.3.6.1.4.1.2011.5.25.219.2.2.5
		-- 1.3.6.1.4.1.2011.5.25.219.2.2.5
		hwBoardInvalid NOTIFICATION-TYPE
			OBJECTS { hwEntityPhysicalIndex, entPhysicalName, hwEntityTrapEntType, hwEntityTrapFaultID, hwEntityTrapReasonDescr, hwEntityOperStatus}
			STATUS current
			DESCRIPTION 
				"This object indicates that a board encounters an overall failure."
			::= { hwBoardTrap 5 }

		
--  1.3.6.1.4.1.2011.5.25.219.2.2.6
		-- 1.3.6.1.4.1.2011.5.25.219.2.2.6
		hwBoardInvalidResume NOTIFICATION-TYPE
			OBJECTS { hwEntityPhysicalIndex, entPhysicalName, hwEntityTrapEntType, hwEntityTrapFaultID, hwEntityTrapReasonDescr, hwEntityOperStatus }
			STATUS current
			DESCRIPTION 
				"This object indicates that a board recovers from an overall failure."
			::= { hwBoardTrap 6 }

		
--  1.3.6.1.4.1.2011.5.25.219.2.2.7
		-- 1.3.6.1.4.1.2011.5.25.219.2.2.7
		hwBoardLeaveMaster NOTIFICATION-TYPE
			OBJECTS { hwEntityPhysicalIndex, entPhysicalName, hwEntityTrapEntType, hwEntityTrapFaultID }
			STATUS current
			DESCRIPTION 
				"This object indicates that a board exits from the active state."
			::= { hwBoardTrap 7 }

		
--  1.3.6.1.4.1.2011.5.25.219.2.2.8
		-- 1.3.6.1.4.1.2011.5.25.219.2.2.8
		hwBoardBecomeMaster NOTIFICATION-TYPE
			OBJECTS { hwEntityPhysicalIndex, entPhysicalName, hwEntityTrapEntType, hwEntityTrapFaultID }
			STATUS current
			DESCRIPTION 
				"This object indicates that a board enters the active state."
			::= { hwBoardTrap 8 }


--  1.3.6.1.4.1.2011.5.25.219.2.2.9
		-- 1.3.6.1.4.1.2011.5.25.219.2.2.9
		hwUpMicroSwitchOpen NOTIFICATION-TYPE
			OBJECTS { hwEntityPhysicalIndex, entPhysicalName, hwEntityTrapEntType, hwEntityTrapFaultID }
			STATUS current
			DESCRIPTION 
				"Up micro switch open."
			::= { hwBoardTrap 9 }


--  1.3.6.1.4.1.2011.5.25.219.2.2.10
		-- 1.3.6.1.4.1.2011.5.25.219.2.2.10
		hwUpMicroSwitchClose NOTIFICATION-TYPE
			OBJECTS { hwEntityPhysicalIndex, entPhysicalName, hwEntityTrapEntType, hwEntityTrapFaultID }
			STATUS current
			DESCRIPTION 
				"Up micro switch close."
			::= { hwBoardTrap 10 }


--  1.3.6.1.4.1.2011.5.25.219.2.2.11
		-- 1.3.6.1.4.1.2011.5.25.219.2.2.9
		hwDownMicroSwitchOpen NOTIFICATION-TYPE
			OBJECTS { hwEntityPhysicalIndex, entPhysicalName, hwEntityTrapEntType, hwEntityTrapFaultID }
			STATUS current
			DESCRIPTION 
				"Down micro switch open."
			::= { hwBoardTrap 11 }


--  1.3.6.1.4.1.2011.5.25.219.2.2.12
		-- 1.3.6.1.4.1.2011.5.25.219.2.2.10
		hwDownMicroSwitchClose NOTIFICATION-TYPE
			OBJECTS { hwEntityPhysicalIndex, entPhysicalName, hwEntityTrapEntType, hwEntityTrapFaultID }
			STATUS current
			DESCRIPTION 
				"Down micro switch close."
			::= { hwBoardTrap 12 }

--  1.3.6.1.4.1.2011.5.25.219.2.2.13
		-- 1.3.6.1.4.1.2011.5.25.219.2.2.13
 		hwBoardPowerOff NOTIFICATION-TYPE
			OBJECTS { hwEntityPhysicalIndex, entPhysicalName, hwEntityTrapEntType, hwEntityTrapFaultID }
			STATUS current
			DESCRIPTION 
				"The LPU is powered off, because this LPU only supports the trunks with index 127 or smaller than 127."
			::= { hwBoardTrap 13 } 	

--  1.3.6.1.4.1.2011.5.25.219.2.2.14
		-- 1.3.6.1.4.1.2011.5.25.219.2.2.14
 		hwBandwidthOfAllCardsExceedsThreshold NOTIFICATION-TYPE
			OBJECTS { hwEntityPhysicalIndex, entPhysicalName, hwEntityTrapEntType}
			STATUS current
			DESCRIPTION 
				"The total bandwidth of all cards exceeds the forwarding capacity of system control board."
			::= { hwBoardTrap 14 } 	

--  1.3.6.1.4.1.2011.5.25.219.2.2.15
		-- 1.3.6.1.4.1.2011.5.25.219.2.2.15
 		hwBoardResetByCmd NOTIFICATION-TYPE
			OBJECTS { hwEntityPhysicalIndex, entPhysicalName, hwEntityTrapEntType, hwEntityTrapReasonDescr, hwEntityOperStatus }
			STATUS current
			DESCRIPTION 
				"This object indicates that the board experiences a command-triggred reset."
			::= { hwBoardTrap 15 } 	
             
--  1.3.6.1.4.1.2011.5.25.219.2.2.16
		-- 1.3.6.1.4.1.2011.5.25.219.2.2.16
 		hwBoardResetByCmdResume NOTIFICATION-TYPE
			OBJECTS { hwEntityPhysicalIndex, entPhysicalName, hwEntityTrapEntType, hwEntityTrapReasonDescr, hwEntityOperStatus }
			STATUS current
			DESCRIPTION 
				"This object indicates that the board recovers from a command-triggred reset."
			::= { hwBoardTrap 16 } 
--  1.3.6.1.4.1.2011.5.25.219.2.2.17
		-- 1.3.6.1.4.1.2011.5.25.219.2.2.17
		hwBoardHeartbeatTimeout NOTIFICATION-TYPE
			OBJECTS { hwEntityPhysicalIndex, entPhysicalName}
			STATUS current
			DESCRIPTION 
				"The heartbeat connection between the board and main control board timed out."
			::= { hwBoardTrap 17 }

--  1.3.6.1.4.1.2011.5.25.219.2.2.18
		-- 1.3.6.1.4.1.2011.5.25.219.2.2.18
		hwBoardHeartbeatResume NOTIFICATION-TYPE
			OBJECTS { hwEntityPhysicalIndex, entPhysicalName }
			STATUS current
			DESCRIPTION 
				"The heartbeat connection between the board and main control board was restored."
			::= { hwBoardTrap 18 }
--  1.3.6.1.4.1.2011.5.25.219.2.2.19
		-- 1.3.6.1.4.1.2011.5.25.219.2.2.19
 		hwBandwidthOfAllCardsExceedsThresholdAlarm NOTIFICATION-TYPE
			OBJECTS { hwEntityPhysicalIndex, entPhysicalName, hwEntityTrapEntType, hwEntityThresholdValue, hwEntityThresholdCurrent}
			STATUS current
			DESCRIPTION 
				"The total bandwidth of all cards exceeds the forwarding capacity of system control board."
			::= { hwBoardTrap 19 }

--  1.3.6.1.4.1.2011.5.25.219.2.2.20
		-- 1.3.6.1.4.1.2011.5.25.219.2.2.20
 		hwBandwidthOfAllCardsExceedsThresholdResume NOTIFICATION-TYPE
			OBJECTS { hwEntityPhysicalIndex, entPhysicalName, hwEntityTrapEntType, hwEntityThresholdValue, hwEntityThresholdCurrent}
			STATUS current
			DESCRIPTION 
				"The total bandwidth of all cards recovered from exceeding the forwarding capacity of system control board."
			::= { hwBoardTrap 20 } 	
--  1.3.6.1.4.1.2011.5.25.219.2.2.21
		-- 1.3.6.1.4.1.2011.5.25.219.2.2.21
 		hwBandwidthOfAllCardsExceedsThresholdFatalAlarm NOTIFICATION-TYPE
			OBJECTS { hwEntityPhysicalIndex, entPhysicalName, hwEntityTrapEntType, hwEntityThresholdCritical, hwEntityThresholdCurrent}
			STATUS current
			DESCRIPTION 
				"The total bandwidth of all cards exceeds the fatal forwarding capacity of system control board."
			::= { hwBoardTrap 21 } 	
--  1.3.6.1.4.1.2011.5.25.219.2.2.22
		-- 1.3.6.1.4.1.2011.5.25.219.2.2.22
 		hwBandwidthOfAllCardsExceedsThresholdFatalResume NOTIFICATION-TYPE
			OBJECTS { hwEntityPhysicalIndex, entPhysicalName, hwEntityTrapEntType, hwEntityThresholdCritical, hwEntityThresholdCurrent}
			STATUS current
			DESCRIPTION 
				"The total bandwidth of all cards recovered from exceeding the fatal forwarding capacity of system control board."
			::= { hwBoardTrap 22 }
--  1.3.6.1.4.1.2011.5.25.219.2.2.23
		-- 1.3.6.1.4.1.2011.5.25.219.2.2.23
 		hwPinchCardReset NOTIFICATION-TYPE
			OBJECTS { hwEntityPhysicalIndex, entPhysicalName, hwEntityTrapEntType, hwEntityTrapReasonDescr, hwEntityOperStatus}
			STATUS current
			DESCRIPTION 
				"The pinch card reset."
			::= { hwBoardTrap 23 } 	
--  1.3.6.1.4.1.2011.5.25.219.2.2.24
		-- 1.3.6.1.4.1.2011.5.25.219.2.2.24
 		hwPinchCardResetResume NOTIFICATION-TYPE
			OBJECTS { hwEntityPhysicalIndex, entPhysicalName, hwEntityTrapEntType, hwEntityTrapReasonDescr, hwEntityOperStatus}
			STATUS current
			DESCRIPTION 
				"The pinch card recovered from reset."
			::= { hwBoardTrap 24 }
			
--  1.3.6.1.4.1.2011.5.25.219.2.2.27
		-- 1.3.6.1.4.1.2011.5.25.219.2.2.27
		hwVBoardInvalid NOTIFICATION-TYPE
			OBJECTS { hwEntityPhysicalIndex, entPhysicalName, hwEntityTrapEntType, hwEntityTrapFaultID, vmName }
			STATUS current
			DESCRIPTION 
				"Board is invalid for some reason."
			::= { hwBoardTrap 27 }
		
--  1.3.6.1.4.1.2011.5.25.219.2.2.28
		-- 1.3.6.1.4.1.2011.5.25.219.2.2.28
		hwVBoardInvalidResume NOTIFICATION-TYPE
			OBJECTS { hwEntityPhysicalIndex, entPhysicalName, hwEntityTrapEntType, hwEntityTrapFaultID, vmName }
			STATUS current
			DESCRIPTION 
				"Board resume from invalid situation."
			::= { hwBoardTrap 28 }

--  1.3.6.1.4.1.2011.5.25.219.2.2.29
		-- 1.3.6.1.4.1.2011.5.25.219.2.2.29
		hwNeedModifyCfgTrap NOTIFICATION-TYPE 
		    OBJECTS { hwEntityTrapFaultID, hwEntityTrapReasonDescr }
			STATUS current
			DESCRIPTION 
				"Before a version upgrade, the system checks the configuration files. If there is any problem, the system informs the user of the problem. After the upgrade, the system informs the user that the device needs to be restarted and configured again."
			::= { hwBoardTrap 29 }

--  1.3.6.1.4.1.2011.5.25.219.2.2.30
		-- 1.3.6.1.4.1.2011.5.25.219.2.2.30
		hwBoardWarning NOTIFICATION-TYPE
			OBJECTS { hwEntityPhysicalIndex, entPhysicalName, hwEntityTrapEntType, hwEntityTrapFaultID}
			STATUS current
			DESCRIPTION 
				"The board experienced a minor fault."
			::= { hwBoardTrap 30 }

--  1.3.6.1.4.1.2011.5.25.219.2.2.31
		-- 1.3.6.1.4.1.2011.5.25.219.2.2.31
		hwBoardWarningResume NOTIFICATION-TYPE
			OBJECTS { hwEntityPhysicalIndex, entPhysicalName, hwEntityTrapEntType, hwEntityTrapFaultID}
			STATUS current
			DESCRIPTION 
				"The board resumed from the minor fault."
			::= { hwBoardTrap 31 }

--  1.3.6.1.4.1.2011.5.25.219.2.2.32
		-- 1.3.6.1.4.1.2011.5.25.219.2.2.32
		hwBoardPortsConflict NOTIFICATION-TYPE
			OBJECTS { hwEntityPhysicalIndex, entPhysicalName, hwEntityTrapEntType, hwEntityTrapFaultID, hwEntityTrapReasonDescr, hwEntityOperStatus }
			STATUS current
			DESCRIPTION 
				"Some ports on the board and subcard conflict with each other."
			::= { hwBoardTrap 32 }

--  1.3.6.1.4.1.2011.5.25.219.2.2.33
		-- 1.3.6.1.4.1.2011.5.25.219.2.2.33
		hwBoardEntityPowerOff NOTIFICATION-TYPE
			OBJECTS { hwEntityPhysicalIndex, entPhysicalName, hwEntityTrapFaultID }
			STATUS current
			DESCRIPTION 
				"The mpu board is powered off."
			::= { hwBoardTrap 33 }

--  1.3.6.1.4.1.2011.5.25.219.2.2.34
		-- 1.3.6.1.4.1.2011.5.25.219.2.2.34
		hwBoardlowmemoryoverload NOTIFICATION-TYPE
			OBJECTS { hwEntityPhysicalIndex, entPhysicalName}
			STATUS current
			DESCRIPTION 
				"The low-end memory usage exceeds 95 percent."
			::= { hwBoardTrap 34 }

--  1.3.6.1.4.1.2011.5.25.219.2.2.35
		-- 1.3.6.1.4.1.2011.5.25.219.2.2.35
		hwBoardlowmemoryoverloadResume NOTIFICATION-TYPE
			OBJECTS { hwEntityPhysicalIndex, entPhysicalName}
			STATUS current
			DESCRIPTION 
				"The low-end memory usage resumes from the overload limit."
			::= { hwBoardTrap 35 }

		-- 1.3.6.1.4.1.2011.5.25.219.2.2.36
		hwBoardAdd NOTIFICATION-TYPE
			OBJECTS { hwEntPhysicalName, hwBoardID }
			STATUS current
			DESCRIPTION 
				"The board was added."
			::= { hwBoardTrap 36 }

		
		-- 1.3.6.1.4.1.2011.5.25.219.2.2.37
		hwBoardDelete NOTIFICATION-TYPE
			OBJECTS { hwEntPhysicalName, hwBoardID }
			STATUS current
			DESCRIPTION 
				"The board was deleted."
			::= { hwBoardTrap 37 }

--  1.3.6.1.4.1.2011.5.25.219.2.2.38
		-- 1.3.6.1.4.1.2011.5.25.219.2.2.38
		hwAllLpuSfuFail NOTIFICATION-TYPE
			STATUS current
			DESCRIPTION 
				"All installed LPUs and SFUs were not registered for a long time."
			::= { hwBoardTrap 38 }

--  1.3.6.1.4.1.2011.5.25.219.2.2.39
		-- 1.3.6.1.4.1.2011.5.25.219.2.2.39
		hwAllLpuSfuFailResume NOTIFICATION-TYPE
			STATUS current
			DESCRIPTION 
				"An LPU or SFU is registered ,or all LPUs and SFUs are powered off."
			::= { hwBoardTrap 39 }
		
--   1.3.6.1.4.1.2011.5.25.219.2.2.40
-- 1.3.6.1.4.1.2011.5.25.219.2.2.40
		-- 1.3.6.1.4.1.2011.5.25.219.2.2.40
		hwBoardUpCoverAlarm NOTIFICATION-TYPE
			STATUS current
			DESCRIPTION 
				"The cover is opened."
			::= { hwBoardTrap 40 }
		
--   1.3.6.1.4.1.2011.5.25.219.2.2.41
-- 1.3.6.1.4.1.2011.5.25.219.2.2.41
		-- 1.3.6.1.4.1.2011.5.25.219.2.2.41
		hwBoardUpCoverResume NOTIFICATION-TYPE
			STATUS current
			DESCRIPTION 
				"The cover is closed."
			::= { hwBoardTrap 41 }
--  1.3.6.1.4.1.2011.5.25.219.2.2.42
		-- 1.3.6.1.4.1.2011.5.25.219.2.2.42
		hwTmPerformanceALarm NOTIFICATION-TYPE
			OBJECTS { hwEntityPhysicalIndex, entPhysicalName, hwEntityTrapEntType, hwEntityTrapFaultID, hwEntityTrapReasonDescr, hwEntityOperStatus}
			STATUS current
			DESCRIPTION 
				"This object indicates that a board encounters an overall failure."
			::= { hwBoardTrap 42 }

		
--  1.3.6.1.4.1.2011.5.25.219.2.2.43
		-- 1.3.6.1.4.1.2011.5.25.219.2.2.43
		hwTmPerformanceResume NOTIFICATION-TYPE
			OBJECTS { hwEntityPhysicalIndex, entPhysicalName, hwEntityTrapEntType, hwEntityTrapFaultID, hwEntityTrapReasonDescr, hwEntityOperStatus }
			STATUS current
			DESCRIPTION 
				"This object indicates that a board recovers from an overall failure."
			::= { hwBoardTrap 43 }
--  1.3.6.1.4.1.2011.5.25.219.2.2.44
		-- 1.3.6.1.4.1.2011.5.25.219.2.2.44
		hwBiosOrBootloaderPwdError NOTIFICATION-TYPE
			OBJECTS { hwEntityPhysicalIndex, entPhysicalName, hwEntityTrapEntType }
			STATUS current
			DESCRIPTION 
				"The bios/bootloader menu password experienced a fault."
			::= { hwBoardTrap 44 }

--  1.3.6.1.4.1.2011.5.25.219.2.2.45
		-- 1.3.6.1.4.1.2011.5.25.219.2.2.45
		hwBiosOrBootloaderPwdErrorResume NOTIFICATION-TYPE
			OBJECTS { hwEntityPhysicalIndex, entPhysicalName, hwEntityTrapEntType }
			STATUS current
			DESCRIPTION 
				"The bios/bootloader menu password resumes from the fault."
			::= { hwBoardTrap 45 }
--  1.3.6.1.4.1.2011.5.25.219.2.2.46
		-- 1.3.6.1.4.1.2011.5.25.219.2.2.46
		hwBootloaderPwdEmpty NOTIFICATION-TYPE
			OBJECTS { hwEntityPhysicalIndex, entPhysicalName, hwEntityTrapEntType }
			STATUS current
			DESCRIPTION 
				"The password of bootloader is empty."
			::= { hwBoardTrap 46 }

--  1.3.6.1.4.1.2011.5.25.219.2.2.47
		-- 1.3.6.1.4.1.2011.5.25.219.2.2.47
		hwBootloaderPwdEmptyResume NOTIFICATION-TYPE
			OBJECTS { hwEntityPhysicalIndex, entPhysicalName, hwEntityTrapEntType }
			STATUS current
			DESCRIPTION 
				"The password of bootloader is set."
			::= { hwBoardTrap 47 }

--  1.3.6.1.4.1.2011.5.25.219.2.2.48
		-- 1.3.6.1.4.1.2011.5.25.219.2.2.48
		hwBoardOffline NOTIFICATION-TYPE
			OBJECTS { hwEntityPhysicalIndex, entPhysicalName }
			STATUS current
			DESCRIPTION 
				"The board is offline."
			::= { hwBoardTrap 48 }

--  1.3.6.1.4.1.2011.5.25.219.2.2.49
		-- 1.3.6.1.4.1.2011.5.25.219.2.2.49
		hwBoardSoftwareNotSupport NOTIFICATION-TYPE
			OBJECTS { hwEntityPhysicalIndex, entPhysicalName }
			STATUS current
			DESCRIPTION 
				"The current or next startup system software is not support the board."
			::= { hwBoardTrap 49 }

--  1.3.6.1.4.1.2011.5.25.219.2.2.50
		-- 1.3.6.1.4.1.2011.5.25.219.2.2.50
		hwForwardEngineInvalid NOTIFICATION-TYPE
			OBJECTS { hwEntityPhysicalIndex, entPhysicalName, hwEntityTrapEntType, hwEntityTrapFaultID }
			STATUS current
			DESCRIPTION 
				"This object indicates that a forwarding engine encounters an overall failure."
			::= { hwBoardTrap 50 }

--  1.3.6.1.4.1.2011.5.25.219.2.2.51
		-- 1.3.6.1.4.1.2011.5.25.219.2.2.51
		hwForwardEngineInvalidResume NOTIFICATION-TYPE
			OBJECTS { hwEntityPhysicalIndex, entPhysicalName, hwEntityTrapEntType, hwEntityTrapFaultID }
			STATUS current
			DESCRIPTION 
				"This object indicates that a forwarding engine recovers from an overall failure."
			::= { hwBoardTrap 51 }       
			
--  1.3.6.1.4.1.2011.5.25.219.2.2.52
		-- 1.3.6.1.4.1.2011.5.25.219.2.2.52
		hwForwardEngineFail NOTIFICATION-TYPE
			OBJECTS { hwEntityPhysicalIndex, entPhysicalName, hwEntityTrapEntType, hwEntityTrapFaultID }
			STATUS current
			DESCRIPTION 
				"This object indicates that a forwarding engine encounters a partial failure."
			::= { hwBoardTrap 52 }

--  1.3.6.1.4.1.2011.5.25.219.2.2.53
		-- 1.3.6.1.4.1.2011.5.25.219.2.2.53
		hwForwardEngineFailResume NOTIFICATION-TYPE
			OBJECTS { hwEntityPhysicalIndex, entPhysicalName, hwEntityTrapEntType, hwEntityTrapFaultID }
			STATUS current
			DESCRIPTION 
				"This object indicates that a forwarding engine recovers from a partial failure."
			::= { hwBoardTrap 53 }

--  1.3.6.1.4.1.2011.5.25.219.2.2.54
		-- 1.3.6.1.4.1.2011.5.25.219.2.2.54
		hwStorageInsufficient NOTIFICATION-TYPE
			OBJECTS { hwEntityPhysicalIndex, entPhysicalName, hwStorageDevName, hwEntityThresholdWarning, hwEntityThresholdCurrent, hwEntityThresholdTip }
			STATUS current
			DESCRIPTION 
				"Storage utilization exceeded the alarm threshold."
			::= { hwBoardTrap 54 }
			
--  1.3.6.1.4.1.2011.5.25.219.2.2.55
		-- 1.3.6.1.4.1.2011.5.25.219.2.2.55
		hwStorageInsufficientResume NOTIFICATION-TYPE
			OBJECTS { hwEntityPhysicalIndex, entPhysicalName, hwStorageDevName, hwEntityThresholdWarning, hwEntityThresholdCurrent }
			STATUS current
			DESCRIPTION 
				"Storage utilization resumed from exceeding the alarm threshold."
			::= { hwBoardTrap 55 }

--  1.3.6.1.4.1.2011.5.25.219.2.2.56
		-- 1.3.6.1.4.1.2011.5.25.219.2.2.56
		hwBoardLicenseActFail NOTIFICATION-TYPE
			OBJECTS { hwGtlItemIndex, hwGtlItemName, entPhysicalIndex, entPhysicalName }
			STATUS current
			DESCRIPTION 
				"The license for board fails to be activated."
			::= { hwBoardTrap 56 }

--  1.3.6.1.4.1.2011.5.25.219.2.2.57
		-- 1.3.6.1.4.1.2011.5.25.219.2.2.57
		hwBoardLicenseActSuccess NOTIFICATION-TYPE
			OBJECTS { hwGtlItemIndex, hwGtlItemName, entPhysicalIndex, entPhysicalName }
			STATUS current
			DESCRIPTION 
				"The license for board is successfully activated."
			::= { hwBoardTrap 57 }
			
--  1.3.6.1.4.1.2011.5.25.219.2.2.58
        -- 1.3.6.1.4.1.2011.5.25.219.2.2.58
        hwCertExpired NOTIFICATION-TYPE
            STATUS current
            DESCRIPTION
               "The certificate will expire."
            ::= { hwBoardTrap 58 }

--  1.3.6.1.4.1.2011.5.25.219.2.2.59
        -- 1.3.6.1.4.1.2011.5.25.219.2.2.59
        hwCertExpiredResume NOTIFICATION-TYPE
			STATUS current
            DESCRIPTION
                "The certificate is updated."
            ::= { hwBoardTrap 59 }

--  1.3.6.1.4.1.2011.5.25.219.2.2.60
        -- 1.3.6.1.4.1.2011.5.25.219.2.2.60
        hwCrlInvalid NOTIFICATION-TYPE
            STATUS current
            DESCRIPTION
               "The Crl is invalid."
            ::= { hwBoardTrap 60 }

--  1.3.6.1.4.1.2011.5.25.219.2.2.61
        -- 1.3.6.1.4.1.2011.5.25.219.2.2.61
        hwCrlInvalidResume NOTIFICATION-TYPE
			STATUS current
            DESCRIPTION
                "The Crl is updated."
            ::= { hwBoardTrap 61 }

--  1.3.6.1.4.1.2011.5.25.219.2.2.62
		-- 1.3.6.1.4.1.2011.5.25.219.2.2.62
		hwSlicePowerFail NOTIFICATION-TYPE
			OBJECTS { hwEntityPhysicalIndex, entPhysicalName }
			STATUS current
			DESCRIPTION 
				"The slice power off is failed."
			::= { hwBoardTrap 62 }

--  1.3.6.1.4.1.2011.5.25.219.2.2.63
		-- 1.3.6.1.4.1.2011.5.25.219.2.2.63
		hwWarmBackFail NOTIFICATION-TYPE
			OBJECTS { hwEntityPhysicalIndex, entPhysicalName }
			STATUS current
			DESCRIPTION 
				"The warm backup is failed."
			::= { hwBoardTrap 63 }

--  1.3.6.1.4.1.2011.5.25.219.2.2.64
		-- 1.3.6.1.4.1.2011.5.25.219.2.2.64
		hwTmStatusChangeAlarm NOTIFICATION-TYPE
			OBJECTS { hwEntityPhysicalIndex, entPhysicalName, hwEntityTrapEntType, hwEntityTrapFaultID, hwEntityTrapReasonDescr, hwEntityOperStatus }
			STATUS current
			DESCRIPTION 
				"The TM deviates from the normal operating state."
			::= { hwBoardTrap 64 }

		
--  1.3.6.1.4.1.2011.5.25.219.2.2.65
		-- 1.3.6.1.4.1.2011.5.25.219.2.2.65
		hwTmStatusChangeAlarmResume NOTIFICATION-TYPE
			OBJECTS { hwEntityPhysicalIndex, entPhysicalName, hwEntityTrapEntType, hwEntityTrapFaultID, hwEntityTrapReasonDescr, hwEntityOperStatus }
			STATUS current
			DESCRIPTION 
				"The TM recovers to the normal state."
			::= { hwBoardTrap 65 }
			
--   1.3.6.1.4.1.2011.5.25.219.2.2.66
-- 1.3.6.1.4.1.2011.5.25.219.2.2.66
		-- 1.3.6.1.4.1.2011.5.25.219.2.2.66
		hwBoardUpCoverStackAlarm NOTIFICATION-TYPE
			OBJECTS {hwSlot, hwLineId}
			STATUS current
			DESCRIPTION 
				"The cover is opened."
			::= { hwBoardTrap 66 }
			
--   1.3.6.1.4.1.2011.5.25.219.2.2.67
-- 1.3.6.1.4.1.2011.5.25.219.2.2.67
		-- 1.3.6.1.4.1.2011.5.25.219.2.2.67
		hwBoardUpCoverStackResume NOTIFICATION-TYPE
			OBJECTS {hwSlot, hwLineId}
			STATUS current
			DESCRIPTION 
				"The cover is closed."
			::= { hwBoardTrap 67 }

-- 1.3.6.1.4.1.2011.5.25.219.2.2.68
		-- 1.3.6.1.4.1.2011.5.25.219.2.2.68
		hwBandwidthOfAllBoardsExceedsThresholdAlarm NOTIFICATION-TYPE
			OBJECTS { hwEntityPhysicalIndex, entPhysicalName, hwEntityThresholdCritical, hwEntityThresholdCurrent}
			STATUS current
			DESCRIPTION 
				"The total bandwidth of all boards exceeded the threshold of the chassis."
			::= { hwBoardTrap 68 }

-- 1.3.6.1.4.1.2011.5.25.219.2.2.69
		-- 1.3.6.1.4.1.2011.5.25.219.2.2.69
		hwBandwidthOfAllBoardsExceedsThresholdAlarmResume NOTIFICATION-TYPE
			OBJECTS { hwEntityPhysicalIndex, entPhysicalName, hwEntityThresholdCritical, hwEntityThresholdCurrent}
			STATUS current
			DESCRIPTION 
				"The total bandwidth of all boards recovered from exceeding the threshold of the chassis. "
			::= { hwBoardTrap 69 }

--  1.3.6.1.4.1.2011.5.25.219.2.2.70
		-- 1.3.6.1.4.1.2011.5.25.219.2.2.70
		hwForwardEngineModelFail NOTIFICATION-TYPE
			OBJECTS { hwEntityPhysicalIndex, entPhysicalName, hwEntityTrapEntType, hwEntityTrapFaultID }
			STATUS current
			DESCRIPTION 
				"This object indicates that a forwarding engine encounters an module failure."
			::= { hwBoardTrap 70 }

--  1.3.6.1.4.1.2011.5.25.219.2.2.71
		-- 1.3.6.1.4.1.2011.5.25.219.2.2.71
		hwForwardEngineModelFailResume NOTIFICATION-TYPE
			OBJECTS { hwEntityPhysicalIndex, entPhysicalName, hwEntityTrapEntType, hwEntityTrapFaultID }
			STATUS current
			DESCRIPTION 
				"This object indicates that a forwarding engine recovers from an module failure."
			::= { hwBoardTrap 71 }

--  1.3.6.1.4.1.2011.5.25.219.2.2.72
		-- 1.3.6.1.4.1.2011.5.25.219.2.2.72
		hwForwardEnginePortFail NOTIFICATION-TYPE
			OBJECTS { hwEntityPhysicalIndex, entPhysicalName, hwEntityTrapEntType, ifName, hwEntityTrapFaultID }
			STATUS current
			DESCRIPTION 
				"This object indicates that a forwarding engine encounters a port failure."
			::= { hwBoardTrap 72 }

--  1.3.6.1.4.1.2011.5.25.219.2.2.73
		-- 1.3.6.1.4.1.2011.5.25.219.2.2.73
		hwForwardEnginePortFailResume NOTIFICATION-TYPE
			OBJECTS { hwEntityPhysicalIndex, entPhysicalName, hwEntityTrapEntType, ifName, hwEntityTrapFaultID }
			STATUS current
			DESCRIPTION 
				"This object indicates that a forwarding engine recovers from a port failure."
			::= { hwBoardTrap 73 }

--  1.3.6.1.4.1.2011.5.25.219.2.2.74
		-- 1.3.6.1.4.1.2011.5.25.219.2.2.74
		hwDeviceRebootTrap NOTIFICATION-TYPE
			OBJECTS { hwDeviceRebootTrapTime, hwDeviceRebootTrapReason }
			STATUS current
			DESCRIPTION 
				"This object indicates that the device reboot."
			::= { hwBoardTrap 74 }
			
--  1.3.6.1.4.1.2011.5.25.219.2.3
		-- 1.3.6.1.4.1.2011.5.25.219.2.3
		hwCardTrap OBJECT IDENTIFIER ::= { hwEntityTraps 3 }
		
--  1.3.6.1.4.1.2011.5.25.219.2.3.1
		-- 1.3.6.1.4.1.2011.5.25.219.2.3.1
		hwCardRemove NOTIFICATION-TYPE
			OBJECTS { hwEntityPhysicalIndex, entPhysicalName, hwEntityTrapEntType, hwEntityTrapFaultID, hwEntityOperStatus}
			STATUS current
			DESCRIPTION 
				"This object indicates that a card cannot be detected."
			::= { hwCardTrap 1 }

		
--  1.3.6.1.4.1.2011.5.25.219.2.3.2
		-- 1.3.6.1.4.1.2011.5.25.219.2.3.2
		hwCardInsert NOTIFICATION-TYPE
			OBJECTS { hwEntityPhysicalIndex, entPhysicalName, hwEntityTrapEntType, hwEntityTrapFaultID, hwEntityOperStatus}
			STATUS current
			DESCRIPTION 
				"This object indicates that a card can be detected."
			::= { hwCardTrap 2 }

		
--  1.3.6.1.4.1.2011.5.25.219.2.3.3
		-- 1.3.6.1.4.1.2011.5.25.219.2.3.3
		hwCardFail NOTIFICATION-TYPE
			OBJECTS { hwEntityPhysicalIndex, entPhysicalName, hwEntityTrapEntType, hwEntityTrapFaultID, hwEntityTrapReasonDescr, hwEntityOperStatus}
			STATUS current
			DESCRIPTION 
				"Card become failure for some reason."
			::= { hwCardTrap 3 }

		
--  1.3.6.1.4.1.2011.5.25.219.2.3.4
		-- 1.3.6.1.4.1.2011.5.25.219.2.3.4
		hwCardFailResume NOTIFICATION-TYPE
			OBJECTS { hwEntityPhysicalIndex, entPhysicalName, hwEntityTrapEntType, hwEntityTrapFaultID, hwEntityTrapReasonDescr, hwEntityOperStatus}
			STATUS current
			DESCRIPTION 
				"Card resume from failure."
			::= { hwCardTrap 4 }

		
--  1.3.6.1.4.1.2011.5.25.219.2.3.5
		-- 1.3.6.1.4.1.2011.5.25.219.2.3.5
		hwCardInvalid NOTIFICATION-TYPE
			OBJECTS { hwEntityPhysicalIndex, entPhysicalName, hwEntityTrapEntType, hwEntityTrapFaultID, hwEntityTrapReasonDescr, hwEntityOperStatus}
			STATUS current
			DESCRIPTION 
				"Card is invalid for some reason."
			::= { hwCardTrap 5 }

		
--  1.3.6.1.4.1.2011.5.25.219.2.3.6
		-- 1.3.6.1.4.1.2011.5.25.219.2.3.6
		hwCardInvalidResume NOTIFICATION-TYPE
			OBJECTS { hwEntityPhysicalIndex, entPhysicalName, hwEntityTrapEntType, hwEntityTrapFaultID, hwEntityTrapReasonDescr, hwEntityOperStatus}
			STATUS current
			DESCRIPTION 
				"Card resume from invalid situation."
			::= { hwCardTrap 6 }

--  1.3.6.1.4.1.2011.5.25.219.2.3.7
		-- 1.3.6.1.4.1.2011.5.25.219.2.3.7
		hwCardResetByCmd NOTIFICATION-TYPE
			OBJECTS { hwEntityPhysicalIndex, entPhysicalName, hwEntityTrapEntType, hwEntityTrapReasonDescr, hwEntityOperStatus}
			STATUS current
			DESCRIPTION 
				"This object indicates that the card experiences a command-triggred reset."
			::= { hwCardTrap 7 }
		
--  1.3.6.1.4.1.2011.5.25.219.2.3.8
		-- 1.3.6.1.4.1.2011.5.25.219.2.3.8
		hwCardResetByCmdResume NOTIFICATION-TYPE
			OBJECTS { hwEntityPhysicalIndex, entPhysicalName, hwEntityTrapEntType, hwEntityTrapReasonDescr, hwEntityOperStatus}
			STATUS current
			DESCRIPTION 
				"This object indicates that the card recovers from a command-triggred reset."
			::= { hwCardTrap 8 }

--  1.3.6.1.4.1.2011.5.25.219.2.3.9
		-- 1.3.6.1.4.1.2011.5.25.219.2.3.9
		hwCardResExceed NOTIFICATION-TYPE
			OBJECTS { hwEntityPhysicalIndex, entPhysicalName, hwEntityTrapFaultID, hwEntityTrapReasonDescr}
			STATUS current
			DESCRIPTION 
				"This object indicates that the resource of card exceeds the maximum limit."
			::= { hwCardTrap 9 }
		
--  1.3.6.1.4.1.2011.5.25.219.2.3.10
		-- 1.3.6.1.4.1.2011.5.25.219.2.3.10
		hwCardResExceedResume NOTIFICATION-TYPE
			OBJECTS { hwEntityPhysicalIndex, entPhysicalName, hwEntityTrapFaultID, hwEntityTrapReasonDescr}
			STATUS current
			DESCRIPTION 
				"This object indicates that the card recovers from resource exceeding the maximum limit."
			::= { hwCardTrap 10 }

--  1.3.6.1.4.1.2011.5.25.219.2.3.11
		-- 1.3.6.1.4.1.2011.5.25.219.2.3.11
		hwCardBandwidthModeChange NOTIFICATION-TYPE
			OBJECTS { hwEntityPhysicalIndex, entPhysicalName, hwEntityTrapEntType, hwEntityBandwidthMode}
			STATUS current
			DESCRIPTION 
				"The bandwidth mode of physical entity is changed."
			::= { hwCardTrap 11 }

        -- 1.3.6.1.4.1.2011.5.25.219.2.3.12
		hwCardSplitChange NOTIFICATION-TYPE
			OBJECTS { hwEntityPhysicalIndex, entPhysicalName }
			STATUS current
			DESCRIPTION 
				"Port split configuration has changed on the card."
			::= { hwCardTrap 12 }
		
--  1.3.6.1.4.1.2011.5.25.219.2.3.13
		hwCardInconsistent NOTIFICATION-TYPE
			OBJECTS { hwEntityPhysicalIndex, entPhysicalName, hwEntityTrapEntType, hwEntityTrapFaultID, hwEntityTrapReasonDescr, hwEntityOperStatus }
			STATUS current
			DESCRIPTION 
				"The card types are different."
			::= { hwCardTrap 13 }

--  1.3.6.1.4.1.2011.5.25.219.2.3.14
		hwRTULicenseActSuccess NOTIFICATION-TYPE
			OBJECTS {hwGtlItemIndex,hwGtlItemName,entPhysicalIndex,entPhysicalName}
			STATUS current
			DESCRIPTION
				"Succeed to activate the RTU license."
			::= {  hwCardTrap 14 }	

--  1.3.6.1.4.1.2011.5.25.219.2.3.15
		-- 1.3.6.1.4.1.2011.5.25.219.2.3.15
		hwCardPortInvalid NOTIFICATION-TYPE
			OBJECTS { hwEntityPhysicalIndex, entPhysicalName, hwEntityTrapEntType, hwEntityTrapFaultID, hwEntityTrapReasonDescr, hwEntityOperStatus}
			STATUS current
			DESCRIPTION 
				"Card port is invalid."
			::= { hwCardTrap 15 }

--  1.3.6.1.4.1.2011.5.25.219.2.4
		-- 1.3.6.1.4.1.2011.5.25.219.2.4
		hwOpticalTrap OBJECT IDENTIFIER ::= { hwEntityTraps 4 }

		
--  1.3.6.1.4.1.2011.5.25.219.2.4.1
		-- 1.3.6.1.4.1.2011.5.25.219.2.4.1
		hwOpticalRemove NOTIFICATION-TYPE
			OBJECTS { hwEntityPhysicalIndex, entPhysicalName, hwEntityTrapFaultID, ifOperStatus, ifAdminStatus, hwOpticalVendorName, hwOpticalVendorSN }
			STATUS current
			DESCRIPTION 
				"Optical Module has been removed."
			::= { hwOpticalTrap 1 }

		
--  1.3.6.1.4.1.2011.5.25.219.2.4.2
		-- 1.3.6.1.4.1.2011.5.25.219.2.4.2
		hwOpticalInsert NOTIFICATION-TYPE
			OBJECTS { hwEntityPhysicalIndex, entPhysicalName, hwEntityTrapFaultID, ifOperStatus, ifAdminStatus, hwOpticalVendorName, hwOpticalVendorSN }
			STATUS current
			DESCRIPTION 
				"Optical Module has been inserted."
			::= { hwOpticalTrap 2 }

		
--  1.3.6.1.4.1.2011.5.25.219.2.4.3
		-- 1.3.6.1.4.1.2011.5.25.219.2.4.3
		hwOpticalFail NOTIFICATION-TYPE
			OBJECTS { hwEntityPhysicalIndex, entPhysicalName, hwEntityTrapFaultID, hwEntityTrapReasonDescr }
			STATUS current
			DESCRIPTION 
				"Optical Module become failure for some reason."
			::= { hwOpticalTrap 3 }

		
--  1.3.6.1.4.1.2011.5.25.219.2.4.4
		-- 1.3.6.1.4.1.2011.5.25.219.2.4.4
		hwOpticalFailResume NOTIFICATION-TYPE
			OBJECTS { hwEntityPhysicalIndex, entPhysicalName, hwEntityTrapFaultID, hwEntityTrapReasonDescr }
			STATUS current
			DESCRIPTION 
				"Optical Module resume from failure."
			::= { hwOpticalTrap 4 }

		
--  1.3.6.1.4.1.2011.5.25.219.2.4.5
		-- 1.3.6.1.4.1.2011.5.25.219.2.4.5
		hwOpticalInvalid NOTIFICATION-TYPE
			OBJECTS { hwEntityPhysicalIndex, entPhysicalName, hwEntityTrapFaultID, hwEntityTrapReasonDescr }
			STATUS current
			DESCRIPTION 
				"Optical Module is invalid for some reason."
			::= { hwOpticalTrap 5 }

		
--  1.3.6.1.4.1.2011.5.25.219.2.4.6
		-- 1.3.6.1.4.1.2011.5.25.219.2.4.6
		hwOpticalInvalidResume NOTIFICATION-TYPE
			OBJECTS { hwEntityPhysicalIndex, entPhysicalName, hwEntityTrapFaultID, hwEntityTrapReasonDescr }
			STATUS current
			DESCRIPTION 
				"Optical Module resume from invalid situation."
			::= { hwOpticalTrap 6 }

        
--  1.3.6.1.4.1.2011.5.25.219.2.4.7
		--  1.3.6.1.4.1.2011.5.25.219.2.4.7
		hwOpticalPowerAlarm NOTIFICATION-TYPE
			OBJECTS { entPhysicalName, hwUserDefAlarmName, hwEntityTrapFaultID }
			STATUS current
			DESCRIPTION 
				"Temperature rise over or fall below the warning alarm threshold.
				Only indicate the temperature of board,card or optical module."
			::= { hwOpticalTrap 7 }

        
--  1.3.6.1.4.1.2011.5.25.219.2.4.8
		--  1.3.6.1.4.1.2011.5.25.219.2.4.8
		hwOpticalPowerAlarmResume NOTIFICATION-TYPE
			OBJECTS { entPhysicalName, hwUserDefAlarmName, hwEntityTrapFaultID }
			STATUS current
			DESCRIPTION 
				"Temperature rise over or fall below the warning alarm threshold.
				Only indicate the temperature of board,card or optical module."
			::= { hwOpticalTrap 8 }

        
--  1.3.6.1.4.1.2011.5.25.219.2.4.9
		-- 1.3.6.1.4.1.2011.5.25.219.2.4.9
		hwOpticalUnAuthorized NOTIFICATION-TYPE
			OBJECTS { hwEntityPhysicalIndex, entPhysicalName, hwEntityTrapFaultID, hwEntityTrapReasonDescr }
			STATUS current
			DESCRIPTION 
				"The optical module authentication alarm occurred."
			::= { hwOpticalTrap 9 }


--  1.3.6.1.4.1.2011.5.25.219.2.4.10
		-- 1.3.6.1.4.1.2011.5.25.219.2.4.10
		hwOpticalUnAuthorizedResume NOTIFICATION-TYPE
			OBJECTS { hwEntityPhysicalIndex, entPhysicalName, hwEntityTrapFaultID }
			STATUS current
			DESCRIPTION 
				"The optical module authentication alarm resumed."
			::= { hwOpticalTrap 10 }


--  1.3.6.1.4.1.2011.5.25.219.2.4.11
		-- 1.3.6.1.4.1.2011.5.25.219.2.4.11
		hwLaserNoFited NOTIFICATION-TYPE
			OBJECTS { hwEntityPhysicalIndex, entPhysicalName }
			STATUS current
			DESCRIPTION 
				"The laser not installed alarm occured."
			::= { hwOpticalTrap 11 }


--  1.3.6.1.4.1.2011.5.25.219.2.4.12
		-- 1.3.6.1.4.1.2011.5.25.219.2.4.12
		hwLaserNoFitedResume NOTIFICATION-TYPE
			OBJECTS { hwEntityPhysicalIndex, entPhysicalName }
			STATUS current
			DESCRIPTION 
				"The laser not installed alarm resumed."
			::= { hwOpticalTrap 12 }
			
--  1.3.6.1.4.1.2011.5.25.219.2.4.13
		-- 1.3.6.1.4.1.2011.5.25.219.2.4.13
		hwOpticalTunableNotMatch NOTIFICATION-TYPE
			OBJECTS { hwEntityPhysicalIndex, entPhysicalName, hwEntityTrapFaultID }
			STATUS current
			DESCRIPTION 
				"Configuration collision occurred between wavelength setting and untunable optical module."
			::= { hwOpticalTrap 13 }
			
--  1.3.6.1.4.1.2011.5.25.219.2.4.14
		-- 1.3.6.1.4.1.2011.5.25.219.2.4.14
		hwOpticalTunableNotMatchResume NOTIFICATION-TYPE
			OBJECTS { hwEntityPhysicalIndex, entPhysicalName, hwEntityTrapFaultID }
			STATUS current
			DESCRIPTION 
				"Configuration collision removed between wavelength setting and untunable optical module."
			::= { hwOpticalTrap 14 }
--  1.3.6.1.4.1.2011.5.25.219.2.4.15
		-- 1.3.6.1.4.1.2011.5.25.219.2.4.15
		hwGpsModuleRemove NOTIFICATION-TYPE
			OBJECTS { hwEntityPhysicalIndex, entPhysicalName }
			STATUS current
			DESCRIPTION 
				"The gps module was removed."
			::= { hwOpticalTrap 15 }


--  1.3.6.1.4.1.2011.5.25.219.2.4.16
                                     -- 1.3.6.1.4.1.2011.5.25.219.2.4.16
                                    hwGpsModuleInsert NOTIFICATION-TYPE
                                                    OBJECTS { hwEntityPhysicalIndex, entPhysicalName }
                                                    STATUS current
                                                    DESCRIPTION 
                                                             "The gps module was inserted."
                                                   ::= { hwOpticalTrap 16 }

--  1.3.6.1.4.1.2011.5.25.219.2.4.17
		-- 1.3.6.1.4.1.2011.5.25.219.2.4.17
		hwOptCfgNotMatch NOTIFICATION-TYPE
			OBJECTS { hwEntityPhysicalIndex, entPhysicalName, hwEntityTrapFaultID, hwEntityTrapReasonDescr }
			STATUS current
			DESCRIPTION 
				"The partial function of optical module failed."
			::= { hwOpticalTrap 17 }

		
--  1.3.6.1.4.1.2011.5.25.219.2.4.18
		-- 1.3.6.1.4.1.2011.5.25.219.2.4.18
		hwOptCfgNotMatchResume NOTIFICATION-TYPE
			OBJECTS { hwEntityPhysicalIndex, entPhysicalName, hwEntityTrapFaultID, hwEntityTrapReasonDescr }
			STATUS current
			DESCRIPTION 
				"The partial function of optical module resumed from partial failure."
			::= { hwOpticalTrap 18 }

--   1.3.6.1.4.1.2011.5.25.219.2.4.5
-- 1.3.6.1.4.1.2011.5.25.219.2.4.5
		-- 1.3.6.1.4.1.2011.5.25.219.2.4.19
		hwOpticalBiasCurrentAlarm NOTIFICATION-TYPE
			OBJECTS { hwEntityPhysicalIndex, entPhysicalName, hwEntityTrapFaultID, hwEntityTrapReasonDescr }
			STATUS current
			DESCRIPTION 
				"Bias current rise over or fall below the warning alarm threshold.
				Only indicate the temperature of board,card or optical module."
			::= { hwOpticalTrap 19 }
		
--   1.3.6.1.4.1.2011.5.25.219.2.4.6
-- 1.3.6.1.4.1.2011.5.25.219.2.4.6
		-- 1.3.6.1.4.1.2011.5.25.219.2.4.20
		hwOpticalBiasCurrentAlarmResume NOTIFICATION-TYPE
			OBJECTS { hwEntityPhysicalIndex, entPhysicalName, hwEntityTrapFaultID, hwEntityTrapReasonDescr }
			STATUS current
			DESCRIPTION 
				"Bias current  rise over or fall below the warning alarm threshold.
				Only indicate the temperature of board,card or optical module."
			::= { hwOpticalTrap 20 }
												   
--  1.3.6.1.4.1.2011.5.25.219.2.5
		-- 1.3.6.1.4.1.2011.5.25.219.2.5
		hwPowerTrap OBJECT IDENTIFIER ::= { hwEntityTraps 5 }

		
--  1.3.6.1.4.1.2011.5.25.219.2.5.1
		-- 1.3.6.1.4.1.2011.5.25.219.2.5.1
		hwPowerRemove NOTIFICATION-TYPE
			OBJECTS { hwEntityPhysicalIndex, entPhysicalName, hwEntityTrapFaultID, hwEntityOperStatus}
			STATUS current
			DESCRIPTION 
				"This object indicates that the power supply cannot be detected."
			::= { hwPowerTrap 1 }

		
--  1.3.6.1.4.1.2011.5.25.219.2.5.2
		-- 1.3.6.1.4.1.2011.5.25.219.2.5.2
		hwPowerInsert NOTIFICATION-TYPE
			OBJECTS { hwEntityPhysicalIndex, entPhysicalName, hwEntityTrapFaultID, hwEntityOperStatus}
			STATUS current
			DESCRIPTION 
				"This object indicates that the power supply can be detected."
			::= { hwPowerTrap 2 }

		
--  1.3.6.1.4.1.2011.5.25.219.2.5.3
		-- 1.3.6.1.4.1.2011.5.25.219.2.5.3
		hwPowerFail NOTIFICATION-TYPE
			OBJECTS { hwEntityPhysicalIndex, entPhysicalName, hwEntityTrapFaultID, hwEntityOperStatus, hwEntityTrapReasonDescr}
			STATUS current
			DESCRIPTION 
				"This object indicates that the power supply encounters a partial failure."
			::= { hwPowerTrap 3 }

		
--  1.3.6.1.4.1.2011.5.25.219.2.5.4
		-- 1.3.6.1.4.1.2011.5.25.219.2.5.4
		hwPowerFailResume NOTIFICATION-TYPE
			OBJECTS { hwEntityPhysicalIndex, entPhysicalName, hwEntityTrapFaultID, hwEntityOperStatus, hwEntityTrapReasonDescr}
			STATUS current
			DESCRIPTION 
				"This object indicates that the power supply recovers from a partial failure."
			::= { hwPowerTrap 4 }

		
--  1.3.6.1.4.1.2011.5.25.219.2.5.5
		-- 1.3.6.1.4.1.2011.5.25.219.2.5.5
		hwPowerInvalid NOTIFICATION-TYPE
			OBJECTS { hwEntityPhysicalIndex, entPhysicalName, hwEntityTrapFaultID, hwEntityOperStatus, hwEntityTrapReasonDescr}
			STATUS current
			DESCRIPTION 
				"This object indicates that the power supply encounters an overall failure."
			::= { hwPowerTrap 5 }

		
--  1.3.6.1.4.1.2011.5.25.219.2.5.6
		-- 1.3.6.1.4.1.2011.5.25.219.2.5.6
		hwPowerInvalidResume NOTIFICATION-TYPE
			OBJECTS { hwEntityPhysicalIndex, entPhysicalName, hwEntityTrapFaultID, hwEntityOperStatus, hwEntityTrapReasonDescr}
			STATUS current
			DESCRIPTION 
				"This object indicates that the power supply recovers from an overall failure."
			::= { hwPowerTrap 6 }

		
--  1.3.6.1.4.1.2011.5.25.219.2.5.7
		-- 1.3.6.1.4.1.2011.5.25.219.2.5.7
		hwPowerUnusable NOTIFICATION-TYPE
			OBJECTS { hwEntityPhysicalIndex, entPhysicalName, hwEntityTrapFaultID }
			STATUS current
			DESCRIPTION 
				"This object indicates that the power supply is unavailable."
			::= { hwPowerTrap 7 }

		
--  1.3.6.1.4.1.2011.5.25.219.2.5.8
		-- 1.3.6.1.4.1.2011.5.25.219.2.5.8
		hwPowerUnusableResume NOTIFICATION-TYPE
			OBJECTS { hwEntityPhysicalIndex, entPhysicalName, hwEntityTrapFaultID }
			STATUS current
			DESCRIPTION 
				"This object indicates that the power supply is unavailable."
			::= { hwPowerTrap 8 }

--  1.3.6.1.4.1.2011.5.25.219.2.5.9
		-- 1.3.6.1.4.1.2011.5.25.219.2.5.9
		hwPowerInsufficient NOTIFICATION-TYPE
			OBJECTS { hwPowerWorkMode, hwExpectPowerWorkMode }
			STATUS current
			DESCRIPTION 
				"AP power supply is insufficient."
			::= { hwPowerTrap 9 }

		
--  1.3.6.1.4.1.2011.5.25.219.2.5.10
		-- 1.3.6.1.4.1.2011.5.25.219.2.5.10
		hwPowerInsufficientResume NOTIFICATION-TYPE
			OBJECTS { hwPowerWorkMode, hwExpectPowerWorkMode }
			STATUS current
			DESCRIPTION 
				"AP power supply insufficient resume."
			::= { hwPowerTrap 10 }

--  1.3.6.1.4.1.2011.5.25.219.2.5.11
		-- 1.3.6.1.4.1.2011.5.25.219.2.5.11
		hwIntegratedPowerFault NOTIFICATION-TYPE
			OBJECTS { hwEntityPhysicalIndex, entPhysicalName, hwEntityTrapFaultID, hwEntityTrapReasonDescr }
			STATUS current
			DESCRIPTION 
				"Integrated power failure."
			::= { hwPowerTrap 11 }

--  1.3.6.1.4.1.2011.5.25.219.2.5.12
		-- 1.3.6.1.4.1.2011.5.25.219.2.5.12
		hwIntegratedPowerFaultResume NOTIFICATION-TYPE
			OBJECTS { hwEntityPhysicalIndex, entPhysicalName, hwEntityTrapFaultID, hwEntityTrapReasonDescr }
			STATUS current
			DESCRIPTION 
				"Integrated power failure resume."
			::= { hwPowerTrap 12 }

--  1.3.6.1.4.1.2011.5.25.219.2.5.13
		-- 1.3.6.1.4.1.2011.5.25.219.2.5.13
		hwPowerLimited NOTIFICATION-TYPE
			OBJECTS { hwPowerWorkMode, hwExpectPowerWorkMode }
			STATUS current
			DESCRIPTION 
				"The AP works in Limited mode due to insufficient power supply."
			::= { hwPowerTrap 13 }
		
--  1.3.6.1.4.1.2011.5.25.219.2.6
		-- 1.3.6.1.4.1.2011.5.25.219.2.6
		hwFanTrap OBJECT IDENTIFIER ::= { hwEntityTraps 6 }

		
--  1.3.6.1.4.1.2011.5.25.219.2.6.1
		-- 1.3.6.1.4.1.2011.5.25.219.2.6.1
		hwFanRemove NOTIFICATION-TYPE
			OBJECTS { hwEntityPhysicalIndex, entPhysicalName, hwEntityTrapFaultID, hwEntityOperStatus}
			STATUS current
			DESCRIPTION 
				"This object indicates that a fan cannot be detected."
			::= { hwFanTrap 1 }

		
--  1.3.6.1.4.1.2011.5.25.219.2.6.2
		-- 1.3.6.1.4.1.2011.5.25.219.2.6.2
		hwFanInsert NOTIFICATION-TYPE
			OBJECTS { hwEntityPhysicalIndex, entPhysicalName, hwEntityTrapFaultID, hwEntityOperStatus}
			STATUS current
			DESCRIPTION 
				"This object indicates that a fan can be detected."
			::= { hwFanTrap 2 }

		
--  1.3.6.1.4.1.2011.5.25.219.2.6.3
		-- 1.3.6.1.4.1.2011.5.25.219.2.6.3
		hwFanFail NOTIFICATION-TYPE
			OBJECTS { hwEntityPhysicalIndex, entPhysicalName, hwEntityTrapFaultID, hwEntityOperStatus, hwEntityTrapReasonDescr}
			STATUS current
			DESCRIPTION 
				"This object indicates that a fan encounters a partial failure."
			::= { hwFanTrap 3 }

		
--  1.3.6.1.4.1.2011.5.25.219.2.6.4
		-- 1.3.6.1.4.1.2011.5.25.219.2.6.4
		hwFanFailResume NOTIFICATION-TYPE
			OBJECTS { hwEntityPhysicalIndex, entPhysicalName, hwEntityTrapFaultID, hwEntityOperStatus, hwEntityTrapReasonDescr}
			STATUS current
			DESCRIPTION 
				"This object indicates that a fan recovers from a partial failure."
			::= { hwFanTrap 4 }

		
--  1.3.6.1.4.1.2011.5.25.219.2.6.5
		-- 1.3.6.1.4.1.2011.5.25.219.2.6.5
		hwFanInvalid NOTIFICATION-TYPE
			OBJECTS { hwEntityPhysicalIndex, entPhysicalName, hwEntityTrapFaultID, hwEntityOperStatus, hwEntityTrapReasonDescr}
			STATUS current
			DESCRIPTION 
				"This object indicates that a fan encounters an overall failure."
			::= { hwFanTrap 5 }

		
--  1.3.6.1.4.1.2011.5.25.219.2.6.6
		-- 1.3.6.1.4.1.2011.5.25.219.2.6.6
		hwFanInvalidResume NOTIFICATION-TYPE
			OBJECTS { hwEntityPhysicalIndex, entPhysicalName, hwEntityTrapFaultID, hwEntityOperStatus, hwEntityTrapReasonDescr}
			STATUS current
			DESCRIPTION 
				"This object indicates that a fan recovers from an overall failure."
			::= { hwFanTrap 6 }

		
--  1.3.6.1.4.1.2011.5.25.219.2.6.7
		-- 1.3.6.1.4.1.2011.5.25.219.2.6.7
		hwFanUnusable NOTIFICATION-TYPE
			OBJECTS { hwEntityPhysicalIndex, entPhysicalName, hwEntityTrapFaultID}
			STATUS current
			DESCRIPTION 
				"This object indicates that a fan is unavailable."
			::= { hwFanTrap 7 }

		
--  1.3.6.1.4.1.2011.5.25.219.2.6.8
		-- 1.3.6.1.4.1.2011.5.25.219.2.6.8
		hwFanUnusableResume NOTIFICATION-TYPE
			OBJECTS { hwEntityPhysicalIndex, entPhysicalName, hwEntityTrapFaultID }
			STATUS current
			DESCRIPTION 
				"This object indicates that a fan becomes available."
			::= { hwFanTrap 8 }
		
--  1.3.6.1.4.1.2011.5.25.219.2.6.9
		-- 1.3.6.1.4.1.2011.5.25.219.2.6.9
		hwFanMinorAlarm NOTIFICATION-TYPE
			OBJECTS { hwEntityPhysicalIndex, entPhysicalName, hwEntityTrapFaultID, hwEntityOperStatus, hwEntityTrapReasonDescr}
			STATUS current
			DESCRIPTION 
				"This object indicates that a minor fault occurred on the fan."
			::= { hwFanTrap 9 }

		
--  1.3.6.1.4.1.2011.5.25.219.2.6.10
		-- 1.3.6.1.4.1.2011.5.25.219.2.6.10
		hwFanMinorAlarmResume NOTIFICATION-TYPE
			OBJECTS { hwEntityPhysicalIndex, entPhysicalName, hwEntityTrapFaultID, hwEntityOperStatus, hwEntityTrapReasonDescr}
			STATUS current
			DESCRIPTION 
				"This object indicates that the fan module recovered from the minor fault."
			::= { hwFanTrap 10 }

		
--  1.3.6.1.4.1.2011.5.25.219.2.7
		-- 1.3.6.1.4.1.2011.5.25.219.2.7
		hwLcdTrap OBJECT IDENTIFIER ::= { hwEntityTraps 7 }

		
--  1.3.6.1.4.1.2011.5.25.219.2.7.1
		-- 1.3.6.1.4.1.2011.5.25.219.2.7.1
		hwLcdRemove NOTIFICATION-TYPE
			OBJECTS { hwEntityPhysicalIndex, entPhysicalName, hwEntityTrapFaultID }
			STATUS current
			DESCRIPTION 
				"Lcd has been removed."
			::= { hwLcdTrap 1 }

		
--  1.3.6.1.4.1.2011.5.25.219.2.7.2
		-- 1.3.6.1.4.1.2011.5.25.219.2.7.2
		hwLcdInsert NOTIFICATION-TYPE
			OBJECTS { hwEntityPhysicalIndex, entPhysicalName, hwEntityTrapFaultID }
			STATUS current
			DESCRIPTION 
				"Lcd has been inserted."
			::= { hwLcdTrap 2 }

		
--  1.3.6.1.4.1.2011.5.25.219.2.7.3
		-- 1.3.6.1.4.1.2011.5.25.219.2.7.3
		hwLcdInvalid NOTIFICATION-TYPE
			OBJECTS { hwEntityPhysicalIndex, entPhysicalName, hwEntityTrapFaultID }
			STATUS current
			DESCRIPTION 
				"Lcd is invalid for some reason."
			::= { hwLcdTrap 3 }

		
--  1.3.6.1.4.1.2011.5.25.219.2.7.4
		-- 1.3.6.1.4.1.2011.5.25.219.2.7.4
		hwLcdInvalidResume NOTIFICATION-TYPE
			OBJECTS { hwEntityPhysicalIndex, entPhysicalName, hwEntityTrapFaultID }
			STATUS current
			DESCRIPTION 
				"Lcd resume from invalid situation."
			::= { hwLcdTrap 4 }

		
--  1.3.6.1.4.1.2011.5.25.219.2.7.5
		-- 1.3.6.1.4.1.2011.5.25.219.2.7.5
		hwLcdUnusable NOTIFICATION-TYPE
			OBJECTS { hwEntityPhysicalIndex, entPhysicalName, hwEntityTrapFaultID }
			STATUS current
			DESCRIPTION 
				"Lcd change to unusable status."
			::= { hwLcdTrap 5 }

		
--  1.3.6.1.4.1.2011.5.25.219.2.7.6
		-- 1.3.6.1.4.1.2011.5.25.219.2.7.6
		hwLcdUnusableResume NOTIFICATION-TYPE
			OBJECTS { hwEntityPhysicalIndex, entPhysicalName, hwEntityTrapFaultID }
			STATUS current
			DESCRIPTION 
				"Lcd change to usable status."
			::= { hwLcdTrap 6 }

		
--  1.3.6.1.4.1.2011.5.25.219.2.8
		-- 1.3.6.1.4.1.2011.5.25.219.2.8
		hwCmuTrap OBJECT IDENTIFIER ::= { hwEntityTraps 8 }

		
--  1.3.6.1.4.1.2011.5.25.219.2.8.1
		-- 1.3.6.1.4.1.2011.5.25.219.2.8.1
		hwCmuRemove NOTIFICATION-TYPE
			OBJECTS { hwEntityPhysicalIndex, entPhysicalName, hwEntityTrapFaultID }
			STATUS current
			DESCRIPTION 
				"This object indicates that a CMU cannot be detected."
			::= { hwCmuTrap 1 }

		
--  1.3.6.1.4.1.2011.5.25.219.2.8.2
		-- 1.3.6.1.4.1.2011.5.25.219.2.8.2
		hwCmuInsert NOTIFICATION-TYPE
			OBJECTS { hwEntityPhysicalIndex, entPhysicalName, hwEntityTrapFaultID }
			STATUS current
			DESCRIPTION 
				"This object indicates that a CMU can be detected."
			::= { hwCmuTrap 2 }

		
--  1.3.6.1.4.1.2011.5.25.219.2.8.3
		-- 1.3.6.1.4.1.2011.5.25.219.2.8.3
		hwCmuInvalid NOTIFICATION-TYPE
			OBJECTS { hwEntityPhysicalIndex, entPhysicalName, hwEntityTrapFaultID }
			STATUS current
			DESCRIPTION 
				"This object indicates that a CMU encounters an overall failure."
			::= { hwCmuTrap 3 }

		
--  1.3.6.1.4.1.2011.5.25.219.2.8.4
		-- 1.3.6.1.4.1.2011.5.25.219.2.8.4
		hwCmuInvalidResume NOTIFICATION-TYPE
			OBJECTS { hwEntityPhysicalIndex, entPhysicalName, hwEntityTrapFaultID }
			STATUS current
			DESCRIPTION 
				"This object indicates that a CMU recovers from an overall failure."
			::= { hwCmuTrap 4 }

		
--  1.3.6.1.4.1.2011.5.25.219.2.8.5
		-- 1.3.6.1.4.1.2011.5.25.219.2.8.5
		hwCmuUnusable NOTIFICATION-TYPE
			OBJECTS { hwEntityPhysicalIndex, entPhysicalName, hwEntityTrapFaultID }
			STATUS current
			DESCRIPTION 
				"This object indicates that a CMU is unavailable."
			::= { hwCmuTrap 5 }

		
--  1.3.6.1.4.1.2011.5.25.219.2.8.6
		-- 1.3.6.1.4.1.2011.5.25.219.2.8.6
		hwCmuUnusableResume NOTIFICATION-TYPE
			OBJECTS { hwEntityPhysicalIndex, entPhysicalName, hwEntityTrapFaultID }
			STATUS current
			DESCRIPTION 
				"This object indicates that a CMU becomes available."
			::= { hwCmuTrap 6 }


--  1.3.6.1.4.1.2011.5.25.219.2.8.7
		-- 1.3.6.1.4.1.2011.5.25.219.2.8.7
		hwCmuFail NOTIFICATION-TYPE
			OBJECTS { hwEntityPhysicalIndex, entPhysicalName, hwEntityTrapFaultID }
			STATUS current
			DESCRIPTION 
				"The CMU experienced a partial failure."
			::= { hwCmuTrap 7 }

		
--  1.3.6.1.4.1.2011.5.25.219.2.8.8
		-- 1.3.6.1.4.1.2011.5.25.219.2.8.8
		hwCmuFailResume NOTIFICATION-TYPE
			OBJECTS { hwEntityPhysicalIndex, entPhysicalName, hwEntityTrapFaultID }
			STATUS current
			DESCRIPTION 
				"The CMU recovered from a partial failure."
			::= { hwCmuTrap 8 }

		
--  1.3.6.1.4.1.2011.5.25.219.2.9
		-- 1.3.6.1.4.1.2011.5.25.219.2.9
		hwCommunicateTrap OBJECT IDENTIFIER ::= { hwEntityTraps 9 }

		
--  1.3.6.1.4.1.2011.5.25.219.2.9.1
		-- 1.3.6.1.4.1.2011.5.25.219.2.9.1
		hwCommunicateError NOTIFICATION-TYPE
			OBJECTS { hwEntityPhysicalIndex, entPhysicalName, hwEntityTrapEntType, hwEntityTrapFaultID, hwEntityCommunicateType, hwEntityTrapReasonDescr
				 }
			STATUS current
			DESCRIPTION 
				"This object indicates that a channel is abnormal."
			::= { hwCommunicateTrap 1 }

		
--  1.3.6.1.4.1.2011.5.25.219.2.9.2
		-- 1.3.6.1.4.1.2011.5.25.219.2.9.2
		hwCommunicateResume NOTIFICATION-TYPE
			OBJECTS { hwEntityPhysicalIndex, entPhysicalName, hwEntityTrapEntType, hwEntityTrapFaultID, hwEntityCommunicateType, hwEntityTrapReasonDescr
				 }
			STATUS current
			DESCRIPTION 
				"This object indicates that a channel recovers from a fault."
			::= { hwCommunicateTrap 2 }

--  1.3.6.1.4.1.2011.5.25.219.2.9.3
		-- 1.3.6.1.4.1.2011.5.25.219.2.9.3
		hwInnerPortPacketCrcErr NOTIFICATION-TYPE
			OBJECTS { hwInnerPortSlotId, hwInnerPortCpuId, hwInnerPortPortId 
				 }
			STATUS current
			DESCRIPTION 
				"The internal communication interface encountered a CRC error."
			::= { hwCommunicateTrap 3 }
		
--  1.3.6.1.4.1.2011.5.25.219.2.9.4
		-- 1.3.6.1.4.1.2011.5.25.219.2.9.4
		hwInnerPortPacketCrcErrResume NOTIFICATION-TYPE
			OBJECTS { hwInnerPortSlotId, hwInnerPortCpuId, hwInnerPortPortId 
				 }
			STATUS current
			DESCRIPTION 
				"The internal communication interface recovered from a CRC error."
			::= { hwCommunicateTrap 4 }
			
--  1.3.6.1.4.1.2011.5.25.219.2.9.5
		-- 1.3.6.1.4.1.2011.5.25.219.2.9.5
		hwInnerPortLinkDown NOTIFICATION-TYPE
			OBJECTS { hwInnerPortSlotId, hwInnerPortCpuId, hwInnerPortPortId 
				 }
			STATUS current
			DESCRIPTION 
				"The link of the internal communication interface went down."
			::= { hwCommunicateTrap 5 }

--  1.3.6.1.4.1.2011.5.25.219.2.9.6
		-- 1.3.6.1.4.1.2011.5.25.219.2.9.6
		hwInnerPortLinkUp NOTIFICATION-TYPE
			OBJECTS { hwInnerPortSlotId, hwInnerPortCpuId, hwInnerPortPortId 
				 }
			STATUS current
			DESCRIPTION 
				"The link status of the internal communication interface went up."
			::= { hwCommunicateTrap 6 }
		
--  1.3.6.1.4.1.2011.5.25.219.2.10
		-- 1.3.6.1.4.1.2011.5.25.219.2.10
		hwEnvironmentTrap OBJECT IDENTIFIER ::= { hwEntityTraps 10 }

		
--  1.3.6.1.4.1.2011.5.25.219.2.10.1
		-- 1.3.6.1.4.1.2011.5.25.219.2.10.1
		hwTempAlarm NOTIFICATION-TYPE
			OBJECTS { hwEntityThresholdType, hwEntityThresholdValue, hwEntityThresholdCurrent, 
				hwEntityTrapFaultID }
			STATUS current
			DESCRIPTION 
				"This object indicates that the ambient temperature is abnormal."
			::= { hwEnvironmentTrap 1 }

		
--  1.3.6.1.4.1.2011.5.25.219.2.10.2
		-- 1.3.6.1.4.1.2011.5.25.219.2.10.2
		hwTempResume NOTIFICATION-TYPE
			OBJECTS { hwEntityThresholdType, hwEntityThresholdValue, hwEntityThresholdCurrent, 
				hwEntityTrapFaultID }
			STATUS current
			DESCRIPTION 
				"This object indicates that the ambient temperature recovers from an abnormality."
			::= { hwEnvironmentTrap 2 }

		
--  1.3.6.1.4.1.2011.5.25.219.2.10.3
		-- 1.3.6.1.4.1.2011.5.25.219.2.10.3
		hwHumidityAlarm NOTIFICATION-TYPE
			OBJECTS { hwEntityThresholdType, hwEntityThresholdValue, hwEntityThresholdCurrent,
			    hwEntityTrapFaultID}
			STATUS current
			DESCRIPTION 
				"This object indicates that the ambient humidity is abnormal."
			::= { hwEnvironmentTrap 3 }

		
--  1.3.6.1.4.1.2011.5.25.219.2.10.4
		-- 1.3.6.1.4.1.2011.5.25.219.2.10.4
		hwHumidityResume NOTIFICATION-TYPE
			OBJECTS { hwEntityThresholdType, hwEntityThresholdValue, hwEntityThresholdCurrent, 
				hwEntityTrapFaultID }
			STATUS current
			DESCRIPTION 
				"This object indicates that the ambient humidity recovers from an abnormality."
			::= { hwEnvironmentTrap 4 }

		
--  1.3.6.1.4.1.2011.5.25.219.2.10.5
		-- 1.3.6.1.4.1.2011.5.25.219.2.10.5
		hwVoltAlarm NOTIFICATION-TYPE
			OBJECTS { hwEntityThresholdType, hwEntityThresholdValue, hwEntityThresholdCurrent, 
				hwEntityTrapFaultID }
			STATUS current
			DESCRIPTION 
				"This object indicates that the ambient voltage is abnormal."
			::= { hwEnvironmentTrap 5 }

		
--  1.3.6.1.4.1.2011.5.25.219.2.10.6
		-- 1.3.6.1.4.1.2011.5.25.219.2.10.6
		hwVoltResume NOTIFICATION-TYPE
			OBJECTS { hwEntityThresholdType, hwEntityThresholdValue, hwEntityThresholdCurrent, 
				hwEntityTrapFaultID }
			STATUS current
			DESCRIPTION 
				"This object indicates that the ambient voltage recovers from an abnormality."
			::= { hwEnvironmentTrap 6 }

		
--  1.3.6.1.4.1.2011.5.25.219.2.10.7
		-- 1.3.6.1.4.1.2011.5.25.219.2.10.7
		hwGateAlarm NOTIFICATION-TYPE
			OBJECTS { hwEntityThresholdType, hwEntityThresholdValue, hwEntityThresholdCurrent, 
				hwEntityTrapFaultID }
			STATUS current
			DESCRIPTION 
				"This object indicates that the door control status is abnormal."
			::= { hwEnvironmentTrap 7 }

		
--  1.3.6.1.4.1.2011.5.25.219.2.10.8
		-- 1.3.6.1.4.1.2011.5.25.219.2.10.8
		hwGateResume NOTIFICATION-TYPE
			OBJECTS { hwEntityThresholdType, hwEntityThresholdValue, hwEntityThresholdCurrent, 
				hwEntityTrapFaultID }
			STATUS current
			DESCRIPTION 
				"This object indicates that the door control status recovers from an abnormality."
			::= { hwEnvironmentTrap 8 }

		
--  1.3.6.1.4.1.2011.5.25.219.2.10.9
		-- 1.3.6.1.4.1.2011.5.25.219.2.10.9
		hwFogAlarm NOTIFICATION-TYPE
			OBJECTS { hwEntityThresholdType, hwEntityThresholdValue, hwEntityThresholdCurrent, 
				hwEntityTrapFaultID }
			STATUS current
			DESCRIPTION 
				"This object indicates that the smoke sensor is abnormal."
			::= { hwEnvironmentTrap 9 }

		
--  1.3.6.1.4.1.2011.5.25.219.2.10.10
		-- 1.3.6.1.4.1.2011.5.25.219.2.10.10
		hwFogResume NOTIFICATION-TYPE
			OBJECTS { hwEntityThresholdType, hwEntityThresholdValue, hwEntityThresholdCurrent, 
				hwEntityTrapFaultID }
			STATUS current
			DESCRIPTION 
				"This object indicates that the smoke sensor recovers from an abnormality."
			::= { hwEnvironmentTrap 10 }

		
--  1.3.6.1.4.1.2011.5.25.219.2.10.11
		-- 1.3.6.1.4.1.2011.5.25.219.2.10.11
		hwUnstableAlarm NOTIFICATION-TYPE
			OBJECTS { hwEntityPhysicalIndex, entPhysicalName, hwEntityTrapEntType, hwEntityTrapFaultID }
			STATUS current
			DESCRIPTION 
				"This object indicates that a physical entity is not securely inserted."
			::= { hwEnvironmentTrap 11 }

		
--  1.3.6.1.4.1.2011.5.25.219.2.10.12
		-- 1.3.6.1.4.1.2011.5.25.219.2.10.12
		hwUnstableResume NOTIFICATION-TYPE
			OBJECTS { hwEntityPhysicalIndex, entPhysicalName, hwEntityTrapEntType, hwEntityTrapFaultID }
			STATUS current
			DESCRIPTION 
				"This object indicates that a physical entity is securely inserted."
			::= { hwEnvironmentTrap 12 }

		
--  1.3.6.1.4.1.2011.5.25.219.2.10.13
		-- 1.3.6.1.4.1.2011.5.25.219.2.10.13
		hwBrdTempAlarm NOTIFICATION-TYPE
			OBJECTS { hwEntityPhysicalIndex, entPhysicalName, hwEntityThresholdType, hwEntityThresholdWarning, hwEntityThresholdCurrent, 
				hwEntityTrapFaultID }
			STATUS current
			DESCRIPTION 
				"This object indicates that the board temperature is abnormal."
			::= { hwEnvironmentTrap 13 }

		
--  1.3.6.1.4.1.2011.5.25.219.2.10.14
		-- 1.3.6.1.4.1.2011.5.25.219.2.10.14
		hwBrdTempResume NOTIFICATION-TYPE
			OBJECTS { hwEntityPhysicalIndex, entPhysicalName, hwEntityThresholdType, hwEntityThresholdWarning, hwEntityThresholdCurrent, 
				hwEntityTrapFaultID }
			STATUS current
			DESCRIPTION 
				"This object indicates that the board temperature recovers from an abnormality."
			::= { hwEnvironmentTrap 14 }

		
--  1.3.6.1.4.1.2011.5.25.219.2.10.15
		-- 1.3.6.1.4.1.2011.5.25.219.2.10.15
		hwBrdTempFatalAlarm NOTIFICATION-TYPE
			OBJECTS { hwEntityPhysicalIndex, entPhysicalName, hwEntityThresholdType, hwEntityThresholdCritical, hwEntityThresholdCurrent, 
				hwEntityTrapFaultID }
			STATUS current
			DESCRIPTION 
				"This object indicates that the board temperature encounters a fatal abnormality."
			::= { hwEnvironmentTrap 15 }

		
--  1.3.6.1.4.1.2011.5.25.219.2.10.16
		-- 1.3.6.1.4.1.2011.5.25.219.2.10.16
		hwBrdTempFatalResume NOTIFICATION-TYPE
			OBJECTS { hwEntityPhysicalIndex, entPhysicalName, hwEntityThresholdType, hwEntityThresholdCritical, hwEntityThresholdCurrent, 
				hwEntityTrapFaultID }
			STATUS current
			DESCRIPTION 
				"This object indicates that the board temperature recovers from a fatal abnormality."
			::= { hwEnvironmentTrap 16 }

--  1.3.6.1.4.1.2011.5.25.219.2.10.17
		-- 1.3.6.1.4.1.2011.5.25.219.2.10.17
		hwPowerFailureAlarm NOTIFICATION-TYPE
			STATUS current
			DESCRIPTION 
				"Power supply failed."
			::= { hwEnvironmentTrap 17 }


--  1.3.6.1.4.1.2011.5.25.219.2.10.18
		-- 1.3.6.1.4.1.2011.5.25.219.2.10.18
		hwPowerFailureResume NOTIFICATION-TYPE
			STATUS current
			DESCRIPTION 
				"Power supply resumed."
			::= { hwEnvironmentTrap 18 }
--  1.3.6.1.4.1.2011.5.25.219.2.10.19
		-- 1.3.6.1.4.1.2011.5.25.219.2.10.19
		hwIOSwitchOneAlarm NOTIFICATION-TYPE
			OBJECTS { hwEntityPhysicalIndex, entPhysicalName, hwUserDefAlarmName }
			STATUS current
			DESCRIPTION 
				"The IO-alarm 1 arise."
			::= { hwEnvironmentTrap 19 }

		
--  1.3.6.1.4.1.2011.5.25.219.2.10.20
		-- 1.3.6.1.4.1.2011.5.25.219.2.10.20
		hwIOSwitchOneAlarmResume NOTIFICATION-TYPE
			OBJECTS { hwEntityPhysicalIndex, entPhysicalName, hwUserDefAlarmName }
			STATUS current
			DESCRIPTION 
				"The IO-alarm 1 resumed."
			::= { hwEnvironmentTrap 20 }

		
--  1.3.6.1.4.1.2011.5.25.219.2.10.21
		-- 1.3.6.1.4.1.2011.5.25.219.2.10.21
		hwIOSwitchTwoAlarm NOTIFICATION-TYPE
			OBJECTS { hwEntityPhysicalIndex, entPhysicalName, hwUserDefAlarmName }
			STATUS current
			DESCRIPTION 
				"The IO-alarm 2 arise."
			::= { hwEnvironmentTrap 21 }

		
--  1.3.6.1.4.1.2011.5.25.219.2.10.22
		-- 1.3.6.1.4.1.2011.5.25.219.2.10.22
		hwIOSwitchTwoAlarmResume NOTIFICATION-TYPE
			OBJECTS { hwEntityPhysicalIndex, entPhysicalName, hwUserDefAlarmName }
			STATUS current
			DESCRIPTION 
				"The IO-alarm 2 resumed."
			::= { hwEnvironmentTrap 22 }

		
--  1.3.6.1.4.1.2011.5.25.219.2.10.23
		-- 1.3.6.1.4.1.2011.5.25.219.2.10.23
		hwIOSwitchThreeAlarm NOTIFICATION-TYPE
			OBJECTS { hwEntityPhysicalIndex, entPhysicalName, hwUserDefAlarmName }
			STATUS current
			DESCRIPTION 
				"The IO-alarm 3 arise."
			::= { hwEnvironmentTrap 23 }

		
--  1.3.6.1.4.1.2011.5.25.219.2.10.24
		-- 1.3.6.1.4.1.2011.5.25.219.2.10.24
		hwIOSwitchThreeAlarmResume NOTIFICATION-TYPE
			OBJECTS { hwEntityPhysicalIndex, entPhysicalName, hwUserDefAlarmName }
			STATUS current
			DESCRIPTION 
				"The IO-alarm 3 resumed."
			::= { hwEnvironmentTrap 24 }

--  1.3.6.1.4.1.2011.5.25.219.2.10.25
		-- 1.3.6.1.4.1.2011.5.25.219.2.10.25
		hwEntityDyingGaspEvent NOTIFICATION-TYPE
		    OBJECTS { hwEntityTrapRelativeResource, hwEntityTrapReasonDescr }
			STATUS current
			DESCRIPTION 
				"Power supply failed."
			::= { hwEnvironmentTrap 25 }

--  1.3.6.1.4.1.2011.5.25.219.2.10.26
		-- 1.3.6.1.4.1.2011.5.25.219.2.10.26
		hwIOSwitchAlarm NOTIFICATION-TYPE
		    OBJECTS { hwEntityPhysicalIndex, entPhysicalName, hwUserDefAlarmName }
			STATUS current
			DESCRIPTION 
				"The IO-alarm arise."
			::= { hwEnvironmentTrap 26 }

--  1.3.6.1.4.1.2011.5.25.219.2.10.27
		-- 1.3.6.1.4.1.2011.5.25.219.2.10.27
		hwIOSwitchAlarmResume NOTIFICATION-TYPE
		    OBJECTS { hwEntityPhysicalIndex, entPhysicalName, hwUserDefAlarmName }
			STATUS current
			DESCRIPTION 
				"The IO-alarm resumed."
			::= { hwEnvironmentTrap 27 }

--  1.3.6.1.4.1.2011.5.25.219.2.11
		-- 1.3.6.1.4.1.2011.5.25.219.2.11
		hwSystemConfigTrap OBJECT IDENTIFIER ::= { hwEntityTraps 11 }

		
--  1.3.6.1.4.1.2011.5.25.219.2.11.1
		-- 1.3.6.1.4.1.2011.5.25.219.2.11.1
		hwSystemConfigError NOTIFICATION-TYPE
			OBJECTS { hwEntityTrapFaultID }
			STATUS current
			DESCRIPTION 
				"System configuration error has been detected."
			::= { hwSystemConfigTrap 1 }

		
--  1.3.6.1.4.1.2011.5.25.219.2.11.2
		-- 1.3.6.1.4.1.2011.5.25.219.2.11.2
		hwSystemConfigResume NOTIFICATION-TYPE
			OBJECTS { hwEntityTrapFaultID }
			STATUS current
			DESCRIPTION 
				"Resume from system configuration error situation."
			::= { hwSystemConfigTrap 2 }

-- 1.3.6.1.4.1.2011.5.25.219.2.11.3
		-- 1.3.6.1.4.1.2011.5.25.219.2.11.3
		hwSystemRollback NOTIFICATION-TYPE
			OBJECTS { hwEntityTrapReasonDescr, hwSoftwareVersion, hwStartupSoftwareFileName }
			STATUS current
			DESCRIPTION 
				"The system was rollback."
			::= { hwSystemConfigTrap 3 }

-- 1.3.6.1.4.1.2011.5.25.219.2.11.4
		-- 1.3.6.1.4.1.2011.5.25.219.2.11.4
		hwVirtualAccessDrvConfigError NOTIFICATION-TYPE
			OBJECTS { hwMasterOpUser, hwAPAdminIP, hwAPID, hwOperation, hwReason }
			STATUS current
			DESCRIPTION 
				"System configuration error has been detected."
			::= { hwSystemConfigTrap 4 }

		-- 1.3.6.1.4.1.2011.5.25.219.2.11.5
		hwPatchDelNeedReStartTrap NOTIFICATION-TYPE
			STATUS current
			DESCRIPTION 
				"The device needs to restart after the patch is deleted."
			::= { hwSystemConfigTrap 5 }

 -- 1.3.6.1.4.1.2011.5.25.219.2.11.6
		-- 1.3.6.1.4.1.2011.5.25.219.2.11.6
		hwSMSReboot NOTIFICATION-TYPE
			OBJECTS { hwEntityTrapReasonDescr }
			STATUS current
			DESCRIPTION 
				"The result of the SMS reboot function."
			::= { hwSystemConfigTrap 6 }
			
 -- 1.3.6.1.4.1.2011.5.25.219.2.11.7			
		-- 1.3.6.1.4.1.2011.5.25.219.2.11.7
		hwVirtualLicenseNearDeadline NOTIFICATION-TYPE
			OBJECTS { hwLicenseRemainTime, hwVirtualLicenseItemName }
			STATUS current
			DESCRIPTION 
				"The virtual license of device is near deadline."
			::= { hwSystemConfigTrap 7 }
			
 -- 1.3.6.1.4.1.2011.5.25.219.2.11.8			
		-- 1.3.6.1.4.1.2011.5.25.219.2.11.8
		hwVirtualLicenseExpire NOTIFICATION-TYPE
			OBJECTS { hwVirtualLicenseItemName }		
			STATUS current
			DESCRIPTION 
				"The virtual license of device has expired."
			::= { hwSystemConfigTrap 8 }

-- 1.3.6.1.4.1.2011.5.25.219.2.11.9			
		-- 1.3.6.1.4.1.2011.5.25.219.2.11.9
		hwVirtualLicenseExpResume NOTIFICATION-TYPE
			OBJECTS { hwVirtualLicenseItemName }		
			STATUS current
			DESCRIPTION 
				"The virtual license expiry alarm was cleared."
			::= { hwSystemConfigTrap 9 }			

			
-- 1.3.6.1.4.1.2011.5.25.219.2.11.10			
		-- 1.3.6.1.4.1.2011.5.25.219.2.11.10
		hwSystemConfigNotMatchTrap NOTIFICATION-TYPE
			OBJECTS { hwEntityPhysicalIndex, entPhysicalName, hwEntityTrapEntType, hwEntityTrapFaultID, hwEntityTrapReasonDescr }		
			STATUS current
			DESCRIPTION 
				"The configuration on the device is different from that on the controller."
			::= { hwSystemConfigTrap 10 }
			
		-- 1.3.6.1.4.1.2011.5.25.219.2.11.11
		hwNetconfDatabaseAbnormal NOTIFICATION-TYPE
			STATUS current
			DESCRIPTION 
				"Database failed to pass the self-test process."
			::= { hwSystemConfigTrap 11 }
		
		-- 1.3.6.1.4.1.2011.5.25.219.2.11.12
		hwNetconfDatabaseRestore NOTIFICATION-TYPE
			STATUS current
			DESCRIPTION 
				"Abnormal database resume."
			::= { hwSystemConfigTrap 12 }			
 
 		-- 1.3.6.1.4.1.2011.5.25.219.2.11.13
		hwCfgDatabaseException NOTIFICATION-TYPE
			STATUS current
			DESCRIPTION 
				"The database has occured exception and the device needs to restart."
			::= { hwSystemConfigTrap 13 }
  
 		-- 1.3.6.1.4.1.2011.5.25.219.2.11.14
		hwVirtualLicenseNearDeadlineResume NOTIFICATION-TYPE
			OBJECTS { hwVirtualLicenseItemName }
			STATUS current
			DESCRIPTION 
				"The virtual license near deadline alarm was cleared."
			::= { hwSystemConfigTrap 14 }
			
		-- 1.3.6.1.4.1.2011.5.25.219.2.11.15
		hwNoConsolePassword NOTIFICATION-TYPE
			STATUS current
			DESCRIPTION 
				"No password is configured for the console."
			::= { hwSystemConfigTrap 15 }
			
--  1.3.6.1.4.1.2011.5.25.219.2.12
		-- 1.3.6.1.4.1.2011.5.25.219.2.12
		hwPortTrap OBJECT IDENTIFIER ::= { hwEntityTraps 12 }

--  1.3.6.1.4.1.2011.5.25.219.2.12.1
		-- 1.3.6.1.4.1.2011.5.25.219.2.12.1
		hwPortDown NOTIFICATION-TYPE
			OBJECTS { hwEntityPhysicalIndex, entPhysicalName, hwEntityTrapFaultID, hwPortDownReason, ifOperStatus, ifAdminStatus }
			STATUS current
			DESCRIPTION 
				"One of the port physical connect down."
			::= { hwPortTrap 1 }

                
--  1.3.6.1.4.1.2011.5.25.219.2.12.2
		-- 1.3.6.1.4.1.2011.5.25.219.2.12.2
 		hwPortUp NOTIFICATION-TYPE
			OBJECTS { hwEntityPhysicalIndex, entPhysicalName, hwEntityTrapFaultID, ifOperStatus, ifAdminStatus }
			STATUS current
			DESCRIPTION 
				"One of the port physical connect up."
			::= { hwPortTrap 2 }

--  1.3.6.1.4.1.2011.5.25.219.2.12.3
		-- 1.3.6.1.4.1.2011.5.25.219.2.12.3
 		hwPortNoSupportOETrap NOTIFICATION-TYPE
			OBJECTS { hwEntityPhysicalIndex, entPhysicalName, hwEntityTrapFaultID }
			STATUS current
			DESCRIPTION 
				"one of the stack port does not support the insertion of the O/E converter."
			::= { hwPortTrap 3 }

--  1.3.6.1.4.1.2011.5.25.219.2.12.4
		-- 1.3.6.1.4.1.2011.5.25.219.2.12.4
 		hwPortRemove NOTIFICATION-TYPE
			OBJECTS { hwEntityPhysicalIndex, entPhysicalName, hwEntityTrapFaultID }
			STATUS current
			DESCRIPTION 
				"One of the port is removed."
			::= { hwPortTrap 4 }

--  1.3.6.1.4.1.2011.5.25.219.2.12.5
		-- 1.3.6.1.4.1.2011.5.25.219.2.12.5
 		hwPortInsert NOTIFICATION-TYPE
			OBJECTS { hwEntityPhysicalIndex, entPhysicalName, hwEntityTrapFaultID }
			STATUS current
			DESCRIPTION 
				"One new port is inserted."
			::= { hwPortTrap 5 }

-- 1.3.6.1.4.1.2011.5.25.219.2.12.8 
                hwPortOpticalPositionInvalid NOTIFICATION-TYPE 
                        OBJECTS { hwEntityPhysicalIndex, entPhysicalName } 
                        STATUS current 
                        DESCRIPTION 
                                " The current port is invalid." 
                        ::= { hwPortTrap 8 } 

                
--  1.3.6.1.4.1.2011.5.25.219.2.12.9 
                -- 1.3.6.1.4.1.2011.5.25.219.2.12.9 
                hwPortOpticalPositionValid NOTIFICATION-TYPE 
                        OBJECTS { hwEntityPhysicalIndex, entPhysicalName } 
                        STATUS current 
                        DESCRIPTION 
                                " The current port is valid." 
                        ::= { hwPortTrap 9}

--  1.3.6.1.4.1.2011.5.25.219.2.12.10
		-- 1.3.6.1.4.1.2011.5.25.219.2.12.10
 		hwPortInvalid NOTIFICATION-TYPE
			OBJECTS { hwEntityPhysicalIndex, entPhysicalName, hwEntityTrapEntType, hwEntityTrapFaultID, hwEntityTrapReasonDescr, hwEntityOperStatus }
			STATUS current
			DESCRIPTION 
				"Port is invalid."
			::= { hwPortTrap 10 }

--  1.3.6.1.4.1.2011.5.25.219.2.12.11
		-- 1.3.6.1.4.1.2011.5.25.219.2.12.11
 		hwPortFail NOTIFICATION-TYPE
			OBJECTS { entPhysicalIndex, entPhysicalName, hwEntityTrapFaultID }
			STATUS current
			DESCRIPTION 
				"The port failed partially."
			::= { hwPortTrap 11 }

--  1.3.6.1.4.1.2011.5.25.219.2.12.12
		-- 1.3.6.1.4.1.2011.5.25.219.2.12.12
 		hwPortFailResume NOTIFICATION-TYPE
			OBJECTS { entPhysicalIndex, entPhysicalName, hwEntityTrapFaultID }
			STATUS current
			DESCRIPTION 
				"The port resumed from partial failure."
			::= { hwPortTrap 12 }
			
--  1.3.6.1.4.1.2011.5.25.219.2.13
		-- 1.3.6.1.4.1.2011.5.25.219.2.13
 		hwUserDefTrap OBJECT IDENTIFIER ::= { hwEntityTraps 13 }


--  1.3.6.1.4.1.2011.5.25.219.2.13.1
		-- 1.3.6.1.4.1.2011.5.25.219.2.13.1
		hwUserDefAlarm NOTIFICATION-TYPE
			OBJECTS { hwEntityPhysicalIndex, entPhysicalName, hwUserDefAlarmName, hwUserDefChannel }
			STATUS current
			DESCRIPTION 
				"User defined alarm has been detected."
			::= { hwUserDefTrap 1 }

                
--  1.3.6.1.4.1.2011.5.25.219.2.13.2
		-- 1.3.6.1.4.1.2011.5.25.219.2.13.2
		hwUserDefResume NOTIFICATION-TYPE
			OBJECTS { hwEntityPhysicalIndex, entPhysicalName, hwUserDefAlarmName, hwUserDefChannel }
			STATUS current
			DESCRIPTION 
				"Resume from User defined alarm."
			::= { hwUserDefTrap 2 }

                
--  1.3.6.1.4.1.2011.5.25.219.2.13.3
		-- 1.3.6.1.4.1.2011.5.25.219.2.13.3
		hwPeerDevPnPTrunkAggregationFailure NOTIFICATION-TYPE
			OBJECTS { hwDeviceMasterESN }
			STATUS current
			DESCRIPTION 
				"The peer device cannot go online because Eth-Trunk auto-negotiation fails."
			::= { hwUserDefTrap 3 }

--  1.3.6.1.4.1.2011.5.25.219.2.13.4
		-- 1.3.6.1.4.1.2011.5.25.219.2.13.4
		hwEsnMismatch NOTIFICATION-TYPE
			OBJECTS { hwEntityPhysicalIndex, entPhysicalName }
			STATUS current
			DESCRIPTION 
				"The ESN of the card does not match the license file."
			::= { hwUserDefTrap 4 }

--  1.3.6.1.4.1.2011.5.25.219.2.13.5
		-- 1.3.6.1.4.1.2011.5.25.219.2.13.5
		hwMacNumMismatch NOTIFICATION-TYPE
			OBJECTS { hwEntityPhysicalIndex, entPhysicalName }
			STATUS current
			DESCRIPTION 
				"The current mac-num of the MPU is less than the system mac-num."
			::= { hwUserDefTrap 5 }

--  1.3.6.1.4.1.2011.5.25.219.2.13.6
		-- 1.3.6.1.4.1.2011.5.25.219.2.13.6
		hwAvaMemInsufficient NOTIFICATION-TYPE
			OBJECTS { hwEntityPhysicalIndex, entPhysicalName, hwAvailableMemory, hwAvailableMemoryThreshold }
			STATUS current
			DESCRIPTION 
				"Insufficient available memory."
			::= { hwUserDefTrap 6 }

--  1.3.6.1.4.1.2011.5.25.219.2.13.7
		-- 1.3.6.1.4.1.2011.5.25.219.2.13.7
		hwAvaMemInsufficientResume NOTIFICATION-TYPE
			OBJECTS { hwEntityPhysicalIndex, entPhysicalName, hwAvailableMemory, hwAvailableMemoryThreshold }
			STATUS current
			DESCRIPTION 
				"Resume from insufficient available memory."
			::= { hwUserDefTrap 7 }
        
--   1.3.6.1.4.1.2011.5.25.219.2.14
		-- 1.3.6.1.4.1.2011.5.25.219.2.14
		hwCPUTrap OBJECT IDENTIFIER ::= { hwEntityTraps 14 }

        
--   1.3.6.1.4.1.2011.5.25.219.2.14.1
		-- 1.3.6.1.4.1.2011.5.25.219.2.14.1
		hwCPUUtilizationRising NOTIFICATION-TYPE
			OBJECTS { hwEntityPhysicalIndex, entPhysicalName, hwEntityThresholdType, hwEntityThresholdWarning, hwEntityThresholdCurrent, 
			hwEntityTrapFaultID }
			STATUS current
			DESCRIPTION 
				"CPU utilization overrun."
			::= { hwCPUTrap 1 }

        
--   1.3.6.1.4.1.2011.5.25.219.2.14.2
		-- 1.3.6.1.4.1.2011.5.25.219.2.14.2
		hwCPUUtilizationResume NOTIFICATION-TYPE
			OBJECTS { hwEntityPhysicalIndex, entPhysicalName, hwEntityThresholdType, hwEntityThresholdWarning, hwEntityThresholdCurrent, 
			hwEntityTrapFaultID }
			STATUS current
			DESCRIPTION 
				"CPU utilization back to normal level"
			::= { hwCPUTrap 2 }

 
--   1.3.6.1.4.1.2011.5.25.219.2.14.3
		-- 1.3.6.1.4.1.2011.5.25.219.2.14.3
		hwCpuFail NOTIFICATION-TYPE
			OBJECTS { hwEntityPhysicalIndex, entPhysicalName, hwEntityTrapFaultID }
			STATUS current
			DESCRIPTION 
				"A fault occurred in the CPU."
			::= { hwCPUTrap 3 }

        	
--   1.3.6.1.4.1.2011.5.25.219.2.14.4
		-- 1.3.6.1.4.1.2011.5.25.219.2.14.4
		hwCpuFailResume NOTIFICATION-TYPE
			OBJECTS { hwEntityPhysicalIndex, entPhysicalName, hwEntityTrapFaultID }
			STATUS current
			DESCRIPTION 
				"The cpu resumed from failure."
			::= { hwCPUTrap 4 }

			
--   1.3.6.1.4.1.2011.5.25.219.2.14.5
		-- 1.3.6.1.4.1.2011.5.25.219.2.14.5
		hwFwdCPUUtilizationRising NOTIFICATION-TYPE
			OBJECTS { hwEntityPhysicalIndex, entPhysicalName, hwEntityThresholdType, hwEntityThresholdWarning, hwEntityThresholdCurrent, 
			hwEntityTrapFaultID }
			STATUS current
			DESCRIPTION 
				"CPU utilization overrun."
			::= { hwCPUTrap 5 }

--   1.3.6.1.4.1.2011.5.25.219.2.14.6
		-- 1.3.6.1.4.1.2011.5.25.219.2.14.6
		hwFwdCPUUtilizationResume NOTIFICATION-TYPE
			OBJECTS { hwEntityPhysicalIndex, entPhysicalName, hwEntityThresholdType, hwEntityThresholdWarning, hwEntityThresholdCurrent, 
			hwEntityTrapFaultID }
			STATUS current
			DESCRIPTION 
				"CPU utilization back to normal level"
			::= { hwCPUTrap 6 }
			 
--   1.3.6.1.4.1.2011.5.25.219.2.15
		-- 1.3.6.1.4.1.2011.5.25.219.2.15
		hwMemoryTrap OBJECT IDENTIFIER ::= { hwEntityTraps 15 }

        
--   1.3.6.1.4.1.2011.5.25.219.2.15.1
		-- 1.3.6.1.4.1.2011.5.25.219.2.15.1
		hwMemUtilizationRising NOTIFICATION-TYPE
			OBJECTS { hwEntityPhysicalIndex, entPhysicalName, hwEntityThresholdType, hwEntityThresholdWarning, hwEntityThresholdCurrent, 
			hwEntityTrapFaultID }
			STATUS current
			DESCRIPTION 
				"Memory utilization overrun."
			::= { hwMemoryTrap 1 }

        
--   1.3.6.1.4.1.2011.5.25.219.2.15.2
		-- 1.3.6.1.4.1.2011.5.25.219.2.15.2
		hwMemUtilizationResume NOTIFICATION-TYPE
			OBJECTS { hwEntityPhysicalIndex, entPhysicalName, hwEntityThresholdType, hwEntityThresholdWarning, hwEntityThresholdCurrent, 
			hwEntityTrapFaultID }
			STATUS current
			DESCRIPTION 
				"Memory utilization back to normal level"
			::= { hwMemoryTrap 2 }

--   1.3.6.1.4.1.2011.5.25.219.2.15.3
		-- 1.3.6.1.4.1.2011.5.25.219.2.15.3
		hwCapMemUtilizationRising NOTIFICATION-TYPE
			OBJECTS { hwCapMemThresholdCurrent, hwCapMemThresholdValue, hwCapMemType }
			STATUS current
			DESCRIPTION 
				"The average value of Cap Memory Utilization exceeds specifications."
			::= { hwMemoryTrap 3 }

--   1.3.6.1.4.1.2011.5.25.219.2.15.4
		-- 1.3.6.1.4.1.2011.5.25.219.2.15.4
		hwCapMemUtilizationResume NOTIFICATION-TYPE
			OBJECTS { hwCapMemThresholdCurrent, hwCapMemThresholdValue, hwCapMemType }
			STATUS current
			DESCRIPTION 
				"The average value of Cap Memory utilization back to normal level."
			::= { hwMemoryTrap 4 }

--   1.3.6.1.4.1.2011.5.25.219.2.16
		-- 1.3.6.1.4.1.2011.5.25.219.2.16     
		hwStorageDevTrap OBJECT IDENTIFIER ::= { hwEntityTraps 16 }

        
--     1.3.6.1.4.1.2011.5.25.219.2.16.1
		-- 1.3.6.1.4.1.2011.5.25.219.2.16.1
		hwStorageDevRemove NOTIFICATION-TYPE
			OBJECTS { entPhysicalName, hwStorageDevName, hwEntityTrapFaultID }
			STATUS current
			DESCRIPTION 
				"Memory utilization overrun."
			::= { hwStorageDevTrap 1 }

        
--     1.3.6.1.4.1.2011.5.25.219.2.16.2
		-- 1.3.6.1.4.1.2011.5.25.219.2.16.2
		hwStorageDevInsert NOTIFICATION-TYPE
			OBJECTS { entPhysicalName, hwStorageDevName, hwEntityTrapFaultID }
			STATUS current
			DESCRIPTION 
				"Memory utilization back to normal level"
			::= { hwStorageDevTrap 2 } 

--   1.3.6.1.4.1.2011.5.25.219.2.17
		-- 1.3.6.1.4.1.2011.5.25.219.2.17
		hwPppTrap OBJECT IDENTIFIER ::= { hwEntityTraps 17 }


--   1.3.6.1.4.1.2011.5.25.219.2.17.1
		-- 1.3.6.1.4.1.2011.5.25.219.2.17.1     
		hwPppLoopbackDetect NOTIFICATION-TYPE
			OBJECTS { hwBaseTrapSeverity, hwBaseTrapProbableCause, hwBaseTrapEventType, ifIndex, ifName }
			STATUS current
			DESCRIPTION 
				"The interface Loopback is detected."
			::= { hwPppTrap 1 }


--   1.3.6.1.4.1.2011.5.25.219.2.17.2
		-- 1.3.6.1.4.1.2011.5.25.219.2.17.2        
		hwPppLoopbackDetResume NOTIFICATION-TYPE
			OBJECTS { hwBaseTrapSeverity, hwBaseTrapProbableCause, hwBaseTrapEventType, ifIndex, ifName }
			STATUS current
			DESCRIPTION 
				"The interface is recovered from Loopback."
			::= { hwPppTrap 2 }       


--   1.3.6.1.4.1.2011.5.25.219.2.18
		-- 1.3.6.1.4.1.2011.5.25.219.2.18
		hwFileStatusTrap OBJECT IDENTIFIER ::= { hwEntityTraps 18 }
	

-- 1.3.6.1.4.1.2011.5.25.219.2.18.1
		-- 1.3.6.1.4.1.2011.5.25.219.2.18.1
		hwFileError NOTIFICATION-TYPE
			OBJECTS { entPhysicalName, hwStorageDevName, hwEntityTrapFaultID }
			STATUS current
			DESCRIPTION 
				"Memory utilization overrun."
			::= { hwFileStatusTrap 1 }


-- 1.3.6.1.4.1.2011.5.25.219.2.18.2
		-- 1.3.6.1.4.1.2011.5.25.219.2.18.2
		hwFileErrorResume NOTIFICATION-TYPE
			OBJECTS { entPhysicalName, hwStorageDevName, hwEntityTrapFaultID }
			STATUS current
			DESCRIPTION 
				"Memory utilization back to normal level"
			::= { hwFileStatusTrap 2 }


--   1.3.6.1.4.1.2011.5.25.219.2.19
-- 1.3.6.1.4.1.2011.5.25.219.2.19
		-- 1.3.6.1.4.1.2011.5.25.219.2.19
		hwUSBTrap OBJECT IDENTIFIER ::= { hwEntityTraps 19 }


-- 1.3.6.1.4.1.2011.5.25.219.2.19.1
		-- 1.3.6.1.4.1.2011.5.25.219.2.19.1
		hwUSBInsert NOTIFICATION-TYPE
			OBJECTS { hwEntityPhysicalIndex, entPhysicalName, hwEntityTrapEntType, hwEntityTrapFaultID }
			STATUS current
			DESCRIPTION 
				"The USB device has been inserted."
			::= { hwUSBTrap 1 }


-- 1.3.6.1.4.1.2011.5.25.219.2.19.2
		-- 1.3.6.1.4.1.2011.5.25.219.2.19.2
		hwUSBRemove NOTIFICATION-TYPE
			OBJECTS { hwEntityPhysicalIndex, entPhysicalName, hwEntityTrapEntType, hwEntityTrapFaultID }
			STATUS current
			DESCRIPTION 
				"The USB device has been removed."
			::= { hwUSBTrap 2 }
 
-- 1.3.6.1.4.1.2011.5.25.219.2.19.3
		-- 1.3.6.1.4.1.2011.5.25.219.2.19.3
		hwUSBUnidentified NOTIFICATION-TYPE
			OBJECTS { hwEntityPhysicalIndex, entPhysicalName, hwEntityTrapEntType, hwEntityTrapFaultID }
			STATUS current
			DESCRIPTION 
				"The USB device is unidentified."
			::= { hwUSBTrap 3 } 

-- 1.3.6.1.4.1.2011.5.25.219.2.19.4
		-- 1.3.6.1.4.1.2011.5.25.219.2.19.4
		hwUSBUnidentifiedResume NOTIFICATION-TYPE
			OBJECTS { hwEntityPhysicalIndex, entPhysicalName, hwEntityTrapEntType, hwEntityTrapFaultID }
			STATUS current
			DESCRIPTION 
				"The USB device resume from unidentified situation."
			::= { hwUSBTrap 4 }   

-- 1.3.6.1.4.1.2011.5.25.219.2.19.5
		-- 1.3.6.1.4.1.2011.5.25.219.2.19.5
		hwUsbStatusChg NOTIFICATION-TYPE
			OBJECTS { hwUsbOperType }
			STATUS current
			DESCRIPTION 
				"The USB device status has been changed."
			::= { hwUSBTrap 5 }	  
			
--  1.3.6.1.4.1.2011.5.25.219.2.20
		-- 1.3.6.1.4.1.2011.5.25.219.2.20
		hwPmuTrap OBJECT IDENTIFIER ::= { hwEntityTraps 20 }

		
--  1.3.6.1.4.1.2011.5.25.219.2.20.1
		-- 1.3.6.1.4.1.2011.5.25.219.2.20.1
		hwPmuRemove NOTIFICATION-TYPE
			OBJECTS { hwEntityPhysicalIndex, entPhysicalName, hwEntityTrapFaultID }
			STATUS current
			DESCRIPTION 
				"This object indicates that a PMU board on the X16A cannot be detected."
			::= { hwPmuTrap 1 }

		
--  1.3.6.1.4.1.2011.5.25.219.2.20.2
		-- 1.3.6.1.4.1.2011.5.25.219.2.20.2
		hwPmuInsert NOTIFICATION-TYPE
			OBJECTS { hwEntityPhysicalIndex, entPhysicalName, hwEntityTrapFaultID }
			STATUS current
			DESCRIPTION 
				"This object indicates that a PMU is inserted into the X16A."
			::= { hwPmuTrap 2 }

		
--  1.3.6.1.4.1.2011.5.25.219.2.20.3
		-- 1.3.6.1.4.1.2011.5.25.219.2.20.3
		hwPmuFail NOTIFICATION-TYPE
			OBJECTS { hwEntityPhysicalIndex, entPhysicalName, hwEntityTrapFaultID,hwEntityTrapReasonDescr }
			STATUS current
			DESCRIPTION 
				"This object indicates that a PMU on the X16A encounters a partial failure."
			::= { hwPmuTrap 3 }

		
--  1.3.6.1.4.1.2011.5.25.219.2.20.4
		-- 1.3.6.1.4.1.2011.5.25.219.2.20.4
		hwPmuFailResume NOTIFICATION-TYPE
			OBJECTS { hwEntityPhysicalIndex, entPhysicalName, hwEntityTrapFaultID }
			STATUS current
			DESCRIPTION 
				"This object indicates that a PMU on the X16A recovers from a partial failure."
			::= { hwPmuTrap 4 }

		
--  1.3.6.1.4.1.2011.5.25.219.2.20.5
		-- 1.3.6.1.4.1.2011.5.25.219.2.20.5
		hwPmuInvalid NOTIFICATION-TYPE
			OBJECTS { hwEntityPhysicalIndex, entPhysicalName, hwEntityTrapFaultID }
			STATUS current
			DESCRIPTION 
				"This object indicates that a PMU on the X16A encounters an overall failure."
			::= { hwPmuTrap 5 }

		
--  1.3.6.1.4.1.2011.5.25.219.2.20.6
		-- 1.3.6.1.4.1.2011.5.25.219.2.20.6
		hwPmuInvalidResume NOTIFICATION-TYPE
			OBJECTS { hwEntityPhysicalIndex, entPhysicalName, hwEntityTrapFaultID }
			STATUS current
			DESCRIPTION 
				"This object indicates that a PMU on the X16A recovers from an overall failure."
			::= { hwPmuTrap 6 }

--   1.3.6.1.4.1.2011.5.25.219.2.21
		-- 1.3.6.1.4.1.2011.5.25.219.2.21
		hwTRAFFICTrap OBJECT IDENTIFIER ::= { hwEntityTraps 21 }

--   1.3.6.1.4.1.2011.5.25.219.2.21.1
		-- 1.3.6.1.4.1.2011.5.25.219.2.21.1
		hwRATEOFTRAFFICRising NOTIFICATION-TYPE
			OBJECTS { hwEntityPhysicalIndex, entPhysicalName, hwEntityTrapFaultID }
			STATUS current
			DESCRIPTION
				"Rate of traffic overrun."
			::= { hwTRAFFICTrap 1 }

--   1.3.6.1.4.1.2011.5.25.219.2.21.2
		-- 1.3.6.1.4.1.2011.5.25.219.2.21.2
		hwRATEOFTRAFFICResume NOTIFICATION-TYPE
			OBJECTS { hwEntityPhysicalIndex, entPhysicalName, hwEntityTrapFaultID }
			STATUS current
			DESCRIPTION
				"Rate of traffic back to normal level."
			::= { hwTRAFFICTrap 2 }

		-- 1.3.6.1.4.1.2011.5.25.219.2.22
		hwBatteryTrap OBJECT IDENTIFIER ::= { hwEntityTraps 22 }

		
		-- 1.3.6.1.4.1.2011.5.25.219.2.22.1
		hwBatteryFull NOTIFICATION-TYPE
			OBJECTS { hwEntityPhysicalIndex, entPhysicalName, hwEntityTrapEntType }
			STATUS current
			DESCRIPTION 
				"battery percent is full ."
			::= { hwBatteryTrap 1 }

		-- 1.3.6.1.4.1.2011.5.25.219.2.22.2
		hwUpsFaultTrap NOTIFICATION-TYPE
			OBJECTS { hwEntityTrapReasonDescr }
			STATUS current
			DESCRIPTION 
				"The UPS battery is faulty."
			::= { hwBatteryTrap 2 }

		-- 1.3.6.1.4.1.2011.5.25.219.2.22.3
		hwUpsFaultResume NOTIFICATION-TYPE
			STATUS current
			DESCRIPTION 
				"The UPS battery fault is rectified."
			::= { hwBatteryTrap 3 }

		-- 1.3.6.1.4.1.2011.5.25.219.2.22.4
		hwUpsPowerLow NOTIFICATION-TYPE
			OBJECTS { hwEntityTrapReasonDescr }
			STATUS current
			DESCRIPTION 
				"Available power of the UPS battery is low."
			::= { hwBatteryTrap 4 }

		-- 1.3.6.1.4.1.2011.5.25.219.2.22.5
		hwUpsPowerFull NOTIFICATION-TYPE
			STATUS current
			DESCRIPTION 
				 "Available power of the UPS battery is restored to the normal range."
			::= { hwBatteryTrap 5 }
		-- 1.3.6.1.4.1.2011.5.25.219.2.22.6
		hwPowerCubeAlarm NOTIFICATION-TYPE
			OBJECTS { hwEntityPhysicalIndex, hwEntityTrapFaultID, entPhysicalName}
			STATUS current
			DESCRIPTION 
				"Indicates that power cube Alarm."
			::= { hwBatteryTrap 6 }
		-- 1.3.6.1.4.1.2011.5.25.219.2.22.7
		hwPowerCubeAlarmResume NOTIFICATION-TYPE
			OBJECTS { hwEntityPhysicalIndex, hwEntityTrapFaultID, entPhysicalName}
			STATUS current
			DESCRIPTION 
				"Indicates that power cube Alarm Resume."
			::= { hwBatteryTrap 7 }
			
		-- 1.3.6.1.4.1.2011.5.25.219.2.22.8
		hwRpsPowerRemove NOTIFICATION-TYPE
			OBJECTS { hwEntityPhysicalIndex, entPhysicalName, hwEntityTrapFaultID}
			STATUS current
			DESCRIPTION 
				"This object indicates that the RPS power supply has been removed."
			::= { hwBatteryTrap 8 }
			
		-- 1.3.6.1.4.1.2011.5.25.219.2.22.9
		hwRpsPowerInsert NOTIFICATION-TYPE
			OBJECTS { hwEntityPhysicalIndex, entPhysicalName, hwEntityTrapFaultID}
			STATUS current
			DESCRIPTION 
				"This object indicates that an RPS power supply has been connected to the device."
			::= { hwBatteryTrap 9 }
			
		-- 1.3.6.1.4.1.2011.5.25.219.2.22.10
		hwRpsPowerOn NOTIFICATION-TYPE
			OBJECTS { hwEntityPhysicalIndex, entPhysicalName, hwEntityTrapFaultID}
			STATUS current
			DESCRIPTION 
				"This object indicates that the RPS power supply starts to provide power."
			::= { hwBatteryTrap 10 }
			
		-- 1.3.6.1.4.1.2011.5.25.219.2.22.11
		hwRpsPowerOff NOTIFICATION-TYPE
			OBJECTS { hwEntityPhysicalIndex, entPhysicalName, hwEntityTrapFaultID}
			STATUS current
			DESCRIPTION 
				"This object indicates that the RPS power supply stops providing power."
			::= { hwBatteryTrap 11 }
			
		-- 1.3.6.1.4.1.2011.5.25.219.2.22.12
		hwRpsFanInvalid NOTIFICATION-TYPE
			OBJECTS { hwEntityPhysicalIndex, entPhysicalName, hwEntityTrapFaultID}
			STATUS current
			DESCRIPTION 
				"This object indicates that fans of the RPS power supply have failed."
			::= { hwBatteryTrap 12 }
			
		-- 1.3.6.1.4.1.2011.5.25.219.2.22.13
		hwRpsFanInvalidResume NOTIFICATION-TYPE
			OBJECTS { hwEntityPhysicalIndex, entPhysicalName, hwEntityTrapFaultID}
			STATUS current
			DESCRIPTION 
				"This object indicates that fans of the RPS power supply have recovered."
			::= { hwBatteryTrap 13 }
			
		-- 1.3.6.1.4.1.2011.5.25.219.2.22.14
		hwRpsTempInvalid NOTIFICATION-TYPE
			OBJECTS { hwEntityPhysicalIndex, entPhysicalName, hwEntityTrapFaultID}
			STATUS current
			DESCRIPTION 
				"This object indicates that temperature of the RPS power supply is out of the normal range."
			::= { hwBatteryTrap 14 }
			
		-- 1.3.6.1.4.1.2011.5.25.219.2.22.15
		hwRpsTempInvalidResume NOTIFICATION-TYPE
			OBJECTS { hwEntityPhysicalIndex, entPhysicalName, hwEntityTrapFaultID}
			STATUS current
			DESCRIPTION 
				"This object indicates that temperature of the RPS power supply has restored to the normal range."
			::= { hwBatteryTrap 15 }

	        -- 1.3.6.1.4.1.2011.5.25.219.2.22.16
		hwBatteryGroupFault NOTIFICATION-TYPE
			OBJECTS { hwEntityPhysicalIndex, entPhysicalName, hwEntityTrapFaultID, hwEntityTrapReasonDescr }
			STATUS current
			DESCRIPTION 
				"This object indicates that a battery group failed."
			::= { hwBatteryTrap 16 }
			
		-- 1.3.6.1.4.1.2011.5.25.219.2.22.17
		hwBatteryGroupFaultResume NOTIFICATION-TYPE
			OBJECTS { hwEntityPhysicalIndex, entPhysicalName, hwEntityTrapFaultID, hwEntityTrapReasonDescr }
			STATUS current
			DESCRIPTION 
				"This object indicates that a battery group recovered."
			::= { hwBatteryTrap 17 }
			
		-- 1.3.6.1.4.1.2011.5.25.219.2.22.18
		hwBatteryFault NOTIFICATION-TYPE
			OBJECTS { hwEntityPhysicalIndex, entPhysicalName, hwEntityTrapFaultID, hwEntityTrapReasonDescr }
			STATUS current
			DESCRIPTION 
				"This object indicates that a battery failed."
			::= { hwBatteryTrap 18 }
			
		-- 1.3.6.1.4.1.2011.5.25.219.2.22.19
		hwBatteryFaultResume NOTIFICATION-TYPE
			OBJECTS { hwEntityPhysicalIndex, entPhysicalName, hwEntityTrapFaultID, hwEntityTrapReasonDescr }
			STATUS current
			DESCRIPTION 
				"This object indicates that a battery recovered."
			::= { hwBatteryTrap 19 }
			
		-- 1.3.6.1.4.1.2011.5.25.219.2.22.20
		hwBatteryMinorFault NOTIFICATION-TYPE
			OBJECTS { hwEntityPhysicalIndex, entPhysicalName, hwEntityTrapFaultID, hwEntityTrapReasonDescr }
			STATUS current
			DESCRIPTION 
				"This object indicates a minor alarm of a battery fault."
			::= { hwBatteryTrap 20 }
			
		-- 1.3.6.1.4.1.2011.5.25.219.2.22.21
		hwBatteryMinorFaultResume NOTIFICATION-TYPE
			OBJECTS { hwEntityPhysicalIndex, entPhysicalName, hwEntityTrapFaultID, hwEntityTrapReasonDescr }
			STATUS current
			DESCRIPTION 
				"This object indicates that a minor alarm of a battery fault is cleared."
			::= { hwBatteryTrap 21 }

--   1.3.6.1.4.1.2011.5.25.219.2.23
		-- 1.3.6.1.4.1.2011.5.25.219.2.23
		hwThreadTrap OBJECT IDENTIFIER ::= { hwEntityTraps 23 }
		
--   1.3.6.1.4.1.2011.5.25.219.2.23.1
		-- 1.3.6.1.4.1.2011.5.25.219.2.23.1
		hwThreadFaultIsolate NOTIFICATION-TYPE
			OBJECTS { entPhysicalName, entPhysicalName, hwEntityPhysicalIndex, hwEntityTrapFaultID }
			STATUS current
			DESCRIPTION
				"The faulty thread has been isolated."
			::= { hwThreadTrap 1 }


		-- 1.3.6.1.4.1.2011.5.25.219.2.24
		hwDiskTrap OBJECT IDENTIFIER ::= { hwEntityTraps 24 }

		
		-- 1.3.6.1.4.1.2011.5.25.219.2.24.1
		hwDiskUtilizationRising NOTIFICATION-TYPE
			OBJECTS { hwEntityPhysicalIndex, entPhysicalName, hwEntityThresholdType, hwEntityThresholdWarning, hwEntityThresholdCurrent, 
				hwEntityTrapFaultID }
			STATUS current
			DESCRIPTION 
				"Disk utilization overrun."
			::= { hwDiskTrap 1 }

		
		-- 1.3.6.1.4.1.2011.5.25.219.2.24.2
		hwDiskUtilizationResume NOTIFICATION-TYPE
			OBJECTS { hwEntityPhysicalIndex, entPhysicalName, hwEntityThresholdType, hwEntityThresholdWarning, hwEntityThresholdCurrent, 
				hwEntityTrapFaultID }
			STATUS current
			DESCRIPTION 
				"Disk utilization back to normal level"
			::= { hwDiskTrap 2 }
-- 1.3.6.1.4.1.2011.5.25.219.2.24.3
		-- 1.3.6.1.4.1.2011.5.25.219.2.24.3
		hwDiskPartitionInValid NOTIFICATION-TYPE
			OBJECTS {hwPartitionEntPhysicalName, hwPartitionName }
			STATUS current
			DESCRIPTION 
				"An alarm was generated when a disk partition was unavailable."
			::= { hwDiskTrap 3 }
			
			
-- 1.3.6.1.4.1.2011.5.25.219.2.24.4
		-- 1.3.6.1.4.1.2011.5.25.219.2.24.4
		hwDiskPartitionInValidResume  NOTIFICATION-TYPE
			OBJECTS { hwPartitionEntPhysicalName, hwPartitionName }
			STATUS current
			DESCRIPTION 
				"The alarm was cleared when the disk partition became available."
			::= { hwDiskTrap 4 }
			
			
-- 1.3.6.1.4.1.2011.5.25.219.2.24.5
		-- 1.3.6.1.4.1.2011.5.25.219.2.24.5
		hwDiskPartitionSpacinsufficient  NOTIFICATION-TYPE
			OBJECTS { hwPartitionEntPhysicalName, hwPartitionName, hwPartitionSpaceFree, hwPartitionSpaceFreeThreshold }
			STATUS current
			DESCRIPTION 
				"An alarm was generated when the disk partition's(except the log partition) available space was below the threshold."
			::= { hwDiskTrap 5}
			
			
-- 1.3.6.1.4.1.2011.5.25.219.2.24.6
		-- 1.3.6.1.4.1.2011.5.25.219.2.24.6
		hwDiskPartitionSpacinsufficientResume  NOTIFICATION-TYPE
			OBJECTS {hwPartitionEntPhysicalName, hwPartitionName, hwPartitionSpaceFree, hwPartitionSpaceFreeThreshold }
			STATUS current
			DESCRIPTION 
				"The alarm was cleared when the disk partition's(except the log partition) available space was above the threshold."
			::= { hwDiskTrap 6 }
			
-- 1.3.6.1.4.1.2011.5.25.219.2.24.7
		-- 1.3.6.1.4.1.2011.5.25.219.2.24.7
		hwDiskPartitionUseageRising  NOTIFICATION-TYPE
			OBJECTS {hwPartitionEntPhysicalName, hwPartitionName, hwPartitionUseage, hwPartitionUseageThreshold }
			STATUS current
			DESCRIPTION 
				"When the disk partition usage(except the log partition) is greater than the specified overload threshold within a statistical period, the alarm is reported."
			::= { hwDiskTrap 7 }

		
-- 1.3.6.1.4.1.2011.5.25.219.2.24.8
		-- 1.3.6.1.4.1.2011.5.25.219.2.24.8
		hwDiskPartitionUseageResume   NOTIFICATION-TYPE
			OBJECTS {hwPartitionEntPhysicalName, hwPartitionName, hwPartitionUseage, hwPartitionUseageThreshold }
			STATUS current
			DESCRIPTION 
				"When the disk partition usage(except the log partition) fell and remained below 10% of the specified overload threshold within a statistical period, the alarm is cleared."
			::= { hwDiskTrap 8}

		hwDiskInvalid   NOTIFICATION-TYPE
			OBJECTS {hwEntPhysicalName}
			STATUS current
			DESCRIPTION 
				"An alarm was generated when the disk was Invalid."
			::= { hwDiskTrap 9}
			
		hwDiskInvalidResume   NOTIFICATION-TYPE
			OBJECTS {hwEntPhysicalName}
			STATUS current
			DESCRIPTION 
				"The alarm was cleared when the disk became available."
			::= { hwDiskTrap 10 }
                                      
                                      hwDiskBadPyhsicalBlocks   NOTIFICATION-TYPE
			OBJECTS {hwEntPhysicalUbiIndex, hwEntCurrentBadPhysicalBlocks,hwEntBadPhysicalBlocksThreshold}
			STATUS current
			DESCRIPTION 
				"An alarm was generated when the disk bad phsical blocks over the threshold."
			::= { hwDiskTrap 11 }

                                     hwDiskErasePyhsicalBlocks   NOTIFICATION-TYPE
			OBJECTS {hwEntPhysicalUbiIndex, hwEntMaxErasePhysicalBlocks,hwEntErasePhysicalBlocksThreshold}
			STATUS current
			DESCRIPTION 
				"An alarm was generated when the disk max erase phsical blocks over the threshold."
			::= { hwDiskTrap 12 }

		-- 1.3.6.1.4.1.2011.5.25.219.2.25
		hwVMTrap OBJECT IDENTIFIER ::= { hwEntityTraps 25 }

		-- 1.3.6.1.4.1.2011.5.25.219.2.25.1
		hwVMResInconsist NOTIFICATION-TYPE
			OBJECTS { hwEntityPhysicalIndex, entPhysicalName, hwEntityTrapEntType, hwEntityTrapFaultID, vmName }
			STATUS current
			DESCRIPTION 
				"Local VM resources are inconsistent with those on the MANO."
			::= { hwVMTrap 1 }

		--  1.3.6.1.4.1.2011.5.25.219.2.25.2
		hwVMResInconsistResume NOTIFICATION-TYPE
			OBJECTS { hwEntityPhysicalIndex, entPhysicalName, hwEntityTrapEntType, hwEntityTrapFaultID, vmName }
			STATUS current
			DESCRIPTION 
				"Local VM resources are consistent with those on the MANO."
			::= { hwVMTrap 2 }

--   1.3.6.1.4.1.2011.5.25.219.2.29
		-- 1.3.6.1.4.1.2011.5.25.219.2.29
		hwDataplaneCpuOverloadTrap OBJECT IDENTIFIER ::= { hwEntityTraps 29 }
		
--   1.3.6.1.4.1.2011.5.25.219.2.29.1
		-- 1.3.6.1.4.1.2011.5.25.219.2.29.1
		hwDataplaneCpuOverloadAlarm NOTIFICATION-TYPE
			OBJECTS { hwEntityPhysicalIndex, entPhysicalName, hwEntityTrapFaultID }
			STATUS current
			DESCRIPTION
				"The dataplane CPU throughput exceeds specifications."
			::= { hwDataplaneCpuOverloadTrap 1 }
			
--   1.3.6.1.4.1.2011.5.25.219.2.29.2
		-- 1.3.6.1.4.1.2011.5.25.219.2.29.2
		hwDataplaneCpuOverloadResume NOTIFICATION-TYPE
			OBJECTS { hwEntityPhysicalIndex, entPhysicalName, hwEntityTrapFaultID }
			STATUS current
			DESCRIPTION
				"The dataplane CPU throughput exceeds specifications alarm cleared."
			::= { hwDataplaneCpuOverloadTrap 2 }

--   1.3.6.1.4.1.2011.5.25.219.2.30
		-- 1.3.6.1.4.1.2011.5.25.219.2.30
		hwInsSpaceLackTrap OBJECT IDENTIFIER ::= { hwEntityTraps 30 }
		
--   1.3.6.1.4.1.2011.5.25.219.2.30.1
		-- 1.3.6.1.4.1.2011.5.25.219.2.30.1
		hwInsSpaceLackAlarm NOTIFICATION-TYPE
			OBJECTS { hwEntityPhysicalIndex, entPhysicalName, hwEntityTrapFaultID }
			STATUS current
			DESCRIPTION
				"The instruction space required for the current configuration exceeds the total instruction space of the forwarding chip."
			::= { hwInsSpaceLackTrap 1 }
			
--   1.3.6.1.4.1.2011.5.25.219.2.30.2
		-- 1.3.6.1.4.1.2011.5.25.219.2.30.2
		hwInsSpaceLackResume NOTIFICATION-TYPE
			OBJECTS { hwEntityPhysicalIndex, entPhysicalName, hwEntityTrapFaultID }
			STATUS current
			DESCRIPTION
				"The instruction space required for the current configuration exceeds the total instruction space of the forwarding chip alarm cleared."
			::= { hwInsSpaceLackTrap 2 }
--   1.3.6.1.4.1.2011.5.25.219.2.31
		-- 1.3.6.1.4.1.2011.5.25.219.2.31
		hwVfpSysCheckErrTrap OBJECT IDENTIFIER ::= { hwEntityTraps 31 }
		
		
--   1.3.6.1.4.1.2011.5.25.219.2.31.1
		-- 1.3.6.1.4.1.2011.5.25.219.2.31.1
		hwVfpSysCheckErr NOTIFICATION-TYPE
			OBJECTS { hwEntityPhysicalIndex, entPhysicalName, hwEntityTrapFaultID, hwEntityTrapEntType}
			STATUS current
			DESCRIPTION
				"A kind of vfp system error occured. "
			::= { hwVfpSysCheckErrTrap 1 }
--   1.3.6.1.4.1.2011.5.25.219.2.31.2
		-- 1.3.6.1.4.1.2011.5.25.219.2.31.2
		hwVfpSysCheckErrResume NOTIFICATION-TYPE
			OBJECTS { hwEntityPhysicalIndex, entPhysicalName, hwEntityTrapFaultID, hwEntityTrapEntType}
			STATUS current
			DESCRIPTION
				"Vfp system error goes away."
			::= { hwVfpSysCheckErrTrap 2 }

--   1.3.6.1.4.1.2011.5.25.219.2.32
		-- 1.3.6.1.4.1.2011.5.25.219.2.32
		hwCapCPUTrap OBJECT IDENTIFIER ::= { hwEntityTraps 32 }

--   1.3.6.1.4.1.2011.5.25.219.2.32.1
		-- 1.3.6.1.4.1.2011.5.25.219.2.32.1
		hwCapCPUUtilizationRising NOTIFICATION-TYPE
			OBJECTS { hwCapCPUThresholdCurrent, hwCapCPUThresholdValue, hwCapCPUThresholdType }
			STATUS current
			DESCRIPTION 
				"The average value of Cap CPU Utilization exceeds specifications."
			::= { hwCapCPUTrap 1 }

--   1.3.6.1.4.1.2011.5.25.219.2.32.2
		-- 1.3.6.1.4.1.2011.5.25.219.2.32.2
		hwCapCPUUtilizationResume NOTIFICATION-TYPE
			OBJECTS { hwCapCPUThresholdCurrent, hwCapCPUThresholdValue, hwCapCPUThresholdType }
			STATUS current
			DESCRIPTION 
				"The average value of Cap CPU utilization back to normal level."
			::= { hwCapCPUTrap 2 }

--   1.3.6.1.4.1.2011.5.25.219.2.32.3
		-- 1.3.6.1.4.1.2011.5.25.219.2.32.3
		hwCapSingleCoreCPUUtilizationRising NOTIFICATION-TYPE
			OBJECTS { hwCapSingleCoreThresholdCurrent, hwCapSingleCoreIndex, hwCapSingleCoreThresholdValue }
			STATUS current
			DESCRIPTION 
				"The value of Cap single core CPU Utilization exceeds specifications."
			::= { hwCapCPUTrap 3 }
			
--   1.3.6.1.4.1.2011.5.25.219.2.32.4
		-- 1.3.6.1.4.1.2011.5.25.219.2.32.4
		hwCapSingleCoreCPUUtilizationResume NOTIFICATION-TYPE
			OBJECTS { hwCapSingleCoreThresholdCurrent, hwCapSingleCoreIndex, hwCapSingleCoreThresholdValue }
			STATUS current
			DESCRIPTION 
				"The value of Cap single core CPU utilization back to normal level."
			::= { hwCapCPUTrap 4 }

--   1.3.6.1.4.1.2011.5.25.219.2.33
		-- 1.3.6.1.4.1.2011.5.25.219.2.33
		hwPDUTrap OBJECT IDENTIFIER ::= { hwEntityTraps 33 }

--   1.3.6.1.4.1.2011.5.25.219.2.33.1
		-- 1.3.6.1.4.1.2011.5.25.219.2.33.1
		hwPduNotPresent NOTIFICATION-TYPE
		OBJECTS { hwEntityPhysicalIndex, entPhysicalName, hwEntityTrapFaultID }
		STATUS current
			DESCRIPTION 
				"The PDU is not present."
			::= { hwPDUTrap 1 }

--   1.3.6.1.4.1.2011.5.25.219.2.33.2
		-- 1.3.6.1.4.1.2011.5.25.219.2.33.2
		hwPduPresent NOTIFICATION-TYPE
			OBJECTS { hwEntityPhysicalIndex, entPhysicalName, hwEntityTrapFaultID }
			STATUS current
			DESCRIPTION 
				"The PDU is present."
			::= { hwPDUTrap 2 }

--   1.3.6.1.4.1.2011.5.25.219.2.33.3
		-- 1.3.6.1.4.1.2011.5.25.219.2.33.3
		hwPduCommLost NOTIFICATION-TYPE
			OBJECTS { hwEntityPhysicalIndex, entPhysicalName, hwEntityTrapFaultID }
			STATUS current
			DESCRIPTION 
				"Communication with the PDU was lost."
			::= { hwPDUTrap 3 }

--   1.3.6.1.4.1.2011.5.25.219.2.33.4
		-- 1.3.6.1.4.1.2011.5.25.219.2.33.4
		hwPduCommLostResume NOTIFICATION-TYPE
			OBJECTS { hwEntityPhysicalIndex, entPhysicalName, hwEntityTrapFaultID }
			STATUS current
			DESCRIPTION 
				"Communication with the PDU was restored."
			::= { hwPDUTrap 4}

--   1.3.6.1.4.1.2011.5.25.219.2.33.5
		-- 1.3.6.1.4.1.2011.5.25.219.2.33.5
		hwPduDmuHardwareFault NOTIFICATION-TYPE
			OBJECTS { hwEntityPhysicalIndex, entPhysicalName, hwEntityTrapFaultID }
			STATUS current
			DESCRIPTION 
				"A hardware fault occurred on the DMU."
			::= { hwPDUTrap 5 }

--   1.3.6.1.4.1.2011.5.25.219.2.33.6
		-- 1.3.6.1.4.1.2011.5.25.219.2.33.6
		hwPduDmuHardwareFaultResume NOTIFICATION-TYPE
			OBJECTS { hwEntityPhysicalIndex, entPhysicalName, hwEntityTrapFaultID }
			STATUS current
			DESCRIPTION 
				"The DMU recovered from a hardware fault."
			::= { hwPDUTrap 6}

--   1.3.6.1.4.1.2011.5.25.219.2.33.7
		-- 1.3.6.1.4.1.2011.5.25.219.2.33.7
		hwPduDMUAutoUpgradeFail NOTIFICATION-TYPE
			OBJECTS { hwEntityPhysicalIndex, entPhysicalName, hwEntityTrapFaultID }
			STATUS current
			DESCRIPTION 
				"The automatic upgrade of DMU was failed."
			::= { hwPDUTrap 7 }

--   1.3.6.1.4.1.2011.5.25.219.2.33.8
		-- 1.3.6.1.4.1.2011.5.25.219.2.33.8
		hwPduDMUAutoUpgradeFailResume NOTIFICATION-TYPE
			OBJECTS { hwEntityPhysicalIndex, entPhysicalName, hwEntityTrapFaultID }
			STATUS current
			DESCRIPTION 
				"Automatic upgrade of the DMU was successful."
			::= { hwPDUTrap 8}

--   1.3.6.1.4.1.2011.5.25.219.2.33.9
		-- 1.3.6.1.4.1.2011.5.25.219.2.33.9
		hwPduDacsHardwareFault NOTIFICATION-TYPE
			OBJECTS { hwEntityPhysicalIndex, entPhysicalName, hwEntityTrapFaultID }
			STATUS current
			DESCRIPTION 
				"A hardware fault occurred on the DACS."
			::= { hwPDUTrap 9 }

--   1.3.6.1.4.1.2011.5.25.219.2.33.10
		-- 1.3.6.1.4.1.2011.5.25.219.2.33.10
		hwPduDacsHardwareFaultResume NOTIFICATION-TYPE
			OBJECTS { hwEntityPhysicalIndex, entPhysicalName, hwEntityTrapFaultID }
			STATUS current
			DESCRIPTION 
				"The DACS recovered from a hardware fault."
			::= { hwPDUTrap 10 }

--   1.3.6.1.4.1.2011.5.25.219.2.33.11
		-- 1.3.6.1.4.1.2011.5.25.219.2.33.11
		hwPduDacsTempAlarm NOTIFICATION-TYPE
			OBJECTS { hwEntityPhysicalIndex, entPhysicalName, hwEntityTrapFaultID }
			STATUS current
			DESCRIPTION 
				"The temperature of the temperature sensor on the DACS is too high."
			::= { hwPDUTrap 11 }

--   1.3.6.1.4.1.2011.5.25.219.2.33.12
		-- 1.3.6.1.4.1.2011.5.25.219.2.33.12
		hwPduDacsTempAlarmResume NOTIFICATION-TYPE
			OBJECTS { hwEntityPhysicalIndex, entPhysicalName, hwEntityTrapFaultID }
			STATUS current
			DESCRIPTION 
				"The temperature of the temperature sensor on the DACS is normal."
			::= { hwPDUTrap 12}

--   1.3.6.1.4.1.2011.5.25.219.2.33.13
		-- 1.3.6.1.4.1.2011.5.25.219.2.33.13
		hwPduDacsI2CChannelFault NOTIFICATION-TYPE
			OBJECTS { hwEntityPhysicalIndex, entPhysicalName, hwEntityTrapFaultID }
			STATUS current
			DESCRIPTION 
				"The IIC channel of the DACS failed."
			::= { hwPDUTrap 13 }

--   1.3.6.1.4.1.2011.5.25.219.2.33.14
		-- 1.3.6.1.4.1.2011.5.25.219.2.33.14
		hwPduDacsI2CChannelFaultResume NOTIFICATION-TYPE
			OBJECTS { hwEntityPhysicalIndex, entPhysicalName, hwEntityTrapFaultID }
			STATUS current
			DESCRIPTION 
				"The IIC channel of the DACS recovered."
			::= { hwPDUTrap 14}

-- 1.3.6.1.4.1.2011.5.25.219.2.34
		-- 1.3.6.1.4.1.2011.5.25.219.2.34
		hwSyslogTrap OBJECT IDENTIFIER ::= { hwEntityTraps 34 }

-- 1.3.6.1.4.1.2011.5.25.219.2.34.1
		-- 1.3.6.1.4.1.2011.5.25.219.2.34.1
		hwReportSyslogInfo NOTIFICATION-TYPE
			OBJECTS { hwSyslogModuleName, hwSyslogTimeStamp, hwSyslogDescription, hwSyslogBrief, hwSyslogSeverityLevel
				 }
			STATUS current
			DESCRIPTION 
				"The information  of syslog trap ."
			::= { hwSyslogTrap 1 }
		                                 
		-- 1.3.6.1.4.1.2011.5.25.219.2.35
		hwEntityNpsTrap OBJECT IDENTIFIER ::= { hwEntityTraps 35 }
		
		-- 1.3.6.1.4.1.2011.5.25.219.2.35.1
		hwEntityNpsPatchInstallFail NOTIFICATION-TYPE
			OBJECTS { hwEntityNpsPatchName, hwEntityNpsPatchVersion, hwEntityNpsErrorDescr }
			STATUS current
			DESCRIPTION 
				"Patch package installation failed."
			::= { hwEntityNpsTrap 1 }
		
		-- 1.3.6.1.4.1.2011.5.25.219.2.35.2
		hwEntityNpsPatchInstallFailResume NOTIFICATION-TYPE
			OBJECTS { hwEntityNpsPatchName, hwEntityNpsPatchVersion, hwEntityNpsErrorDescr }
			STATUS current
			DESCRIPTION 
				"The patch-installation failure alarm is cleared."
			::= { hwEntityNpsTrap 2 }
		
		-- 1.3.6.1.4.1.2011.5.25.219.2.35.3
		hwEntityNpsPatchPacketError NOTIFICATION-TYPE
			OBJECTS { hwEntityNpsPatchName }
			STATUS current
			DESCRIPTION 
				"Patch package file error."
			::= { hwEntityNpsTrap 3 }
		
		-- 1.3.6.1.4.1.2011.5.25.219.2.35.4
		hwEntityNpsPatchPacketErrorResume NOTIFICATION-TYPE
			OBJECTS { hwEntityNpsPatchName }
			STATUS current
			DESCRIPTION 
				"Patch package file error restored."
			::= { hwEntityNpsTrap 4 }
		
		-- 1.3.6.1.4.1.2011.5.25.219.2.35.5
		hwEntityNpsSysConfigError NOTIFICATION-TYPE
			OBJECTS { hwEntityNpsErrorCode }
			STATUS current
			DESCRIPTION 
				"A system configuration error occurs."
			::= { hwEntityNpsTrap 5 }
		
		-- 1.3.6.1.4.1.2011.5.25.219.2.35.6
		hwEntityNpsSysConfigErrorResume NOTIFICATION-TYPE
			OBJECTS { hwEntityNpsErrorCode }
			STATUS current
			DESCRIPTION 
				"The system configuration error has been rectified."
			::= { hwEntityNpsTrap 6 }
		
		-- 1.3.6.1.4.1.2011.5.25.219.2.35.7
		hwEntityNpsSslCertInvalidEarlyWarning NOTIFICATION-TYPE
			OBJECTS { hwEntityNpsCertType, hwEntityNpsCertRemainDays }
			STATUS current
			DESCRIPTION 
				"The inner SSL certificate will expire."
			::= { hwEntityNpsTrap 7 }
		
		-- 1.3.6.1.4.1.2011.5.25.219.2.35.8
		hwEntityNpsSslCertInvalidEarlyResume NOTIFICATION-TYPE
			OBJECTS { hwEntityNpsCertType }
			STATUS current
			DESCRIPTION 
				"The inner SSL certificate was upgraded."
			::= { hwEntityNpsTrap 8 }
		
		-- 1.3.6.1.4.1.2011.5.25.219.2.35.9
		hwEntityNpsSslCertInvalid NOTIFICATION-TYPE
			OBJECTS { hwEntityNpsCertType, hwEntityNpsErrorDescr }
			STATUS current
			DESCRIPTION 
				"The inner SSL certificate was invalid."
			::= { hwEntityNpsTrap 9 }
		
		-- 1.3.6.1.4.1.2011.5.25.219.2.35.10
		hwEntityNpsSslCertInvalidResume NOTIFICATION-TYPE
			OBJECTS { hwEntityNpsCertType }
			STATUS current
			DESCRIPTION 
				"The inner SSL certificate was repaired."
			::= { hwEntityNpsTrap 10 }
		
		-- 1.3.6.1.4.1.2011.5.25.219.2.35.11
		hwEntityNpsDiskPartitionUsageExceedingThreshold NOTIFICATION-TYPE
			OBJECTS { hwEntityNpsVMName, hwEntityNpsPartitionName, hwEntityNpsPartitionUsage, hwEntityNpsPartitionUsageThreshold }
			STATUS current
			DESCRIPTION 
				"The disk usage exceeded the pre-set overload threshold."
			::= { hwEntityNpsTrap 11 }
		
		-- 1.3.6.1.4.1.2011.5.25.219.2.35.12
		hwEntityNpsDiskPartitionUsageExceedingThresholdResume NOTIFICATION-TYPE
			OBJECTS { hwEntityNpsVMName, hwEntityNpsPartitionName, hwEntityNpsPartitionUsage, hwEntityNpsPartitionUsageThreshold }
			STATUS current
			DESCRIPTION 
				"The disk partition usage of the VM was 10% lower than the preset threshold."
			::= { hwEntityNpsTrap 12 }
		
		-- 1.3.6.1.4.1.2011.5.25.219.2.35.13
		hwEntityNpsDiskPartitionUnavailable NOTIFICATION-TYPE
			OBJECTS { hwEntityNpsVMName, hwEntityNpsPartitionName }
			STATUS current
			DESCRIPTION 
				"The VM's disk partition was unavailable."
			::= { hwEntityNpsTrap 13 }
		
		-- 1.3.6.1.4.1.2011.5.25.219.2.35.14
		hwEntityNpsDiskPartitionUnavailableResume NOTIFICATION-TYPE
			OBJECTS { hwEntityNpsVMName, hwEntityNpsPartitionName }
			STATUS current
			DESCRIPTION 
				"The fault where the VM's disk partition was unavailable was rectified."
			::= { hwEntityNpsTrap 14 }
		
		-- 1.3.6.1.4.1.2011.5.25.219.2.35.15
		hwEntityNpsDiskPartitionSpaceInsufficient NOTIFICATION-TYPE
			OBJECTS { hwEntityNpsVMName, hwEntityNpsPartitionName, hwEntityNpsPartitionAvailableSpace, hwEntityNpsPartitionCapacityThreshold }
			STATUS current
			DESCRIPTION 
				"The disk partition's available space was less than the threshold."
			::= { hwEntityNpsTrap 15 }
		
		-- 1.3.6.1.4.1.2011.5.25.219.2.35.16
		hwEntityNpsDiskPartitionSpaceInsufficientResume NOTIFICATION-TYPE
			OBJECTS { hwEntityNpsVMName, hwEntityNpsPartitionName, hwEntityNpsPartitionAvailableSpace, hwEntityNpsPartitionCapacityThreshold }
			STATUS current
			DESCRIPTION 
				"The disk partition's available space was more than the threshold."
			::= { hwEntityNpsTrap 16 }
		
		-- 1.3.6.1.4.1.2011.5.25.219.2.35.17
		hwEntityNpsExecutableFilesIncomplete NOTIFICATION-TYPE
			OBJECTS { hwEntityNpsVMName }
			STATUS current
			DESCRIPTION 
				"The file check failed."
			::= { hwEntityNpsTrap 17 }
		
		-- 1.3.6.1.4.1.2011.5.25.219.2.35.18
		hwEntityNpsExecutableFilesIncompleteResume NOTIFICATION-TYPE
			OBJECTS { hwEntityNpsVMName }
			STATUS current
			DESCRIPTION 
				"The file check success."
			::= { hwEntityNpsTrap 18 }
		
		-- 1.3.6.1.4.1.2011.5.25.219.2.35.19
		hwEntityNpsSoftwareIntegrityError NOTIFICATION-TYPE
			OBJECTS { hwEntityNpsVNFCType, hwEntityNpsAPPType, hwEntityNpsSoftwareVersionType, hwEntityNpsSoftwareVersionID }
			STATUS current
			DESCRIPTION 
				"The software check failed."
			::= { hwEntityNpsTrap 19 }
		
		-- 1.3.6.1.4.1.2011.5.25.219.2.35.20
		hwEntityNpsSoftwareIntegrityErrorResume NOTIFICATION-TYPE
			OBJECTS { hwEntityNpsVNFCType, hwEntityNpsAPPType, hwEntityNpsSoftwareVersionType, hwEntityNpsSoftwareVersionID }
			STATUS current
			DESCRIPTION 
				"The software check success."
			::= { hwEntityNpsTrap 20 }
		
		-- 1.3.6.1.4.1.2011.5.25.219.2.35.21
		hwEntityNpsOMUSyncFail NOTIFICATION-TYPE
			OBJECTS { hwEntityNpsErrorDescr }
			STATUS current
			DESCRIPTION 
				"Data failed to be synchronized from the master OMU to the slave OMU."
			::= { hwEntityNpsTrap 21 }
		
		-- 1.3.6.1.4.1.2011.5.25.219.2.35.22
		hwEntityNpsOMUSyncFailResume NOTIFICATION-TYPE
			OBJECTS { hwEntityNpsErrorDescr }
			STATUS current
			DESCRIPTION 
				"A master/slave OMU data synchronization failure was removed, or the slave OMU became absent after a master/slave OMU data synchronization failure occurred."
			::= { hwEntityNpsTrap 22 }
		
		-- 1.3.6.1.4.1.2011.5.25.219.2.35.23
		hwEntityNpsVMDiskUnavailable NOTIFICATION-TYPE
			OBJECTS { hwEntityNpsVMName }
			STATUS current
			DESCRIPTION 
				"A fault occurs on the VM disk."
			::= { hwEntityNpsTrap 23 }
		
		-- 1.3.6.1.4.1.2011.5.25.219.2.35.24
		hwEntityNpsVMDiskUnavailableResume NOTIFICATION-TYPE
			OBJECTS { hwEntityNpsVMName }
			STATUS current
			DESCRIPTION 
				"The fault on the VM disk is cleared."
			::= { hwEntityNpsTrap 24 }
		
		-- 1.3.6.1.4.1.2011.5.25.219.2.35.25
		hwEntityNpsDatabaseRestoreFail NOTIFICATION-TYPE
			OBJECTS { hwEntityNpsErrorDescr }
			STATUS current
			DESCRIPTION 
				"Database Restoration Failure."
			::= { hwEntityNpsTrap 25 }
		
		-- 1.3.6.1.4.1.2011.5.25.219.2.35.26
		hwEntityNpsSSLCertExpired NOTIFICATION-TYPE
			OBJECTS { hwEntityNpsCertName, hwEntityNpsCertType, hwEntityNpsCertValidBeginTime, hwEntityNpsCertValidEndTime }
			STATUS current
			DESCRIPTION 
				"The certificate already expired."
			::= { hwEntityNpsTrap 26 }
		
		-- 1.3.6.1.4.1.2011.5.25.219.2.35.27
		hwEntityNpsSSLCertExpiredEarlyWarning NOTIFICATION-TYPE
			OBJECTS { hwEntityNpsCertName, hwEntityNpsCertType, hwEntityNpsCertValidBeginTime, hwEntityNpsCertValidEndTime }
			STATUS current
			DESCRIPTION 
				"The SSL certificate will expire."
			::= { hwEntityNpsTrap 27 }
		
		-- 1.3.6.1.4.1.2011.5.25.219.2.35.28
		hwEntityNpsVMResInconsist NOTIFICATION-TYPE
			OBJECTS { hwEntityNpsVMName, hwEntityNpsVMID, hwEntityNpsPhyVMID, hwEntityNpsErrorDescr }
			STATUS current
			DESCRIPTION 
				"Local VM resources are inconsistent with those on the MANO."
			::= { hwEntityNpsTrap 28 }
		
		-- 1.3.6.1.4.1.2011.5.25.219.2.35.29
		hwEntityNpsVMResInconsistResume NOTIFICATION-TYPE
			OBJECTS { hwEntityNpsVMName, hwEntityNpsVMID, hwEntityNpsPhyVMID, hwEntityNpsErrorDescr }
			STATUS current
			DESCRIPTION 
				"Local VM resources are consistent with those on the MANO."
			::= { hwEntityNpsTrap 29 }
		
		-- 1.3.6.1.4.1.2011.5.25.219.2.35.30
		hwEntityNpsVmFault NOTIFICATION-TYPE
			OBJECTS { hwEntityNpsVMName, hwEntityNpsVMID, hwEntityNpsPhyVMID, hwEntityNpsErrorDescr }
			STATUS current
			DESCRIPTION 
				"A fault occurs on a VM."
			::= { hwEntityNpsTrap 30 }
		
		-- 1.3.6.1.4.1.2011.5.25.219.2.35.31
		hwEntityNpsVmFaultResume NOTIFICATION-TYPE
			OBJECTS { hwEntityNpsVMName, hwEntityNpsVMID, hwEntityNpsPhyVMID, hwEntityNpsErrorDescr }
			STATUS current
			DESCRIPTION 
				"The fault on the VM is cleared."
			::= { hwEntityNpsTrap 31 }
		
		-- 1.3.6.1.4.1.2011.5.25.219.2.35.32
		hwEntityNpsVNFMConnectFault NOTIFICATION-TYPE
			OBJECTS { hwEntityNpsIPAddress, hwEntityNpsPort, hwEntityNpsErrorDescr }
			STATUS current
			DESCRIPTION 
				"The connection between VNF and VNFM fault was faulty."
			::= { hwEntityNpsTrap 32 }
		
		-- 1.3.6.1.4.1.2011.5.25.219.2.35.33
		hwEntityNpsVNFMConnectResume NOTIFICATION-TYPE
			OBJECTS { hwEntityNpsIPAddress, hwEntityNpsPort, hwEntityNpsErrorDescr }
			STATUS current
			DESCRIPTION 
				"The connection between VNF and VNFM fault was rectified."
			::= { hwEntityNpsTrap 33 }
		
		-- 1.3.6.1.4.1.2011.5.25.219.2.35.34
		hwEntityNpsFabricOamPlaneDown NOTIFICATION-TYPE
			OBJECTS { hwEntityNpsLocalVMName, hwEntityNpsRemoteVMName, hwEntityNpsNetworkPlaneID }
			STATUS current
			DESCRIPTION 
				"Fabric plane goes Down."
			::= { hwEntityNpsTrap 34 }
		
		-- 1.3.6.1.4.1.2011.5.25.219.2.35.35
		hwEntityNpsFabricOamPlaneDownResume NOTIFICATION-TYPE
			OBJECTS { hwEntityNpsLocalVMName, hwEntityNpsRemoteVMName, hwEntityNpsNetworkPlaneID }
			STATUS current
			DESCRIPTION 
				"Fabric plane down alarm was cleared."
			::= { hwEntityNpsTrap 35 }
		
		-- 1.3.6.1.4.1.2011.5.25.219.2.35.36
		hwEntityNpsFabricLinkSubhealthy NOTIFICATION-TYPE
			OBJECTS { hwEntityNpsLocalVMName, hwEntityNpsRemoteVMName, hwEntityNpsNetworkPlaneID, hwEntityNpsNetworkErrorThreshold }
			STATUS current
			DESCRIPTION 
				"Fabric link goes subhealthy."
			::= { hwEntityNpsTrap 36 }
		
		-- 1.3.6.1.4.1.2011.5.25.219.2.35.37
		hwEntityNpsFabricLinkSubhealthyResume NOTIFICATION-TYPE
			OBJECTS { hwEntityNpsLocalVMName, hwEntityNpsRemoteVMName, hwEntityNpsNetworkPlaneID, hwEntityNpsNetworkErrorThreshold }
			STATUS current
			DESCRIPTION 
				"Fabric link resume from subhealthy."
			::= { hwEntityNpsTrap 37 }
		
		-- 1.3.6.1.4.1.2011.5.25.219.2.35.38
		hwEntityNpsDriverTypeMismatch NOTIFICATION-TYPE
			OBJECTS { hwEntityNpsVMName, hwEntityNpsDriverVendor, hwEntityNpsDeviceID, hwEntityNpsDriverType, hwEntityNpsErrorDescr
				 }
			STATUS current
			DESCRIPTION 
				"Load vNIC driver failure."
			::= { hwEntityNpsTrap 38 }
		
		-- 1.3.6.1.4.1.2011.5.25.219.2.35.39
		hwEntityNpsDriverTypeMismatchResume NOTIFICATION-TYPE
			OBJECTS { hwEntityNpsVMName, hwEntityNpsDriverVendor, hwEntityNpsDeviceID, hwEntityNpsDriverType, hwEntityNpsErrorDescr
				 }
			STATUS current
			DESCRIPTION 
				"Load vNIC driver success."
			::= { hwEntityNpsTrap 39 }
		
		-- 1.3.6.1.4.1.2011.5.25.219.2.35.40
		hwEntityNpsRuCreateFail NOTIFICATION-TYPE
			OBJECTS { hwEntityNpsVMName, hwEntityNpsVNFCName, hwEntityNpsRUName, hwEntityNpsErrorDescr }
			STATUS current
			DESCRIPTION 
				"The VM create RU failed."
			::= { hwEntityNpsTrap 40 }
		
		-- 1.3.6.1.4.1.2011.5.25.219.2.35.41
		hwEntityNpsRuCreateFailResume NOTIFICATION-TYPE
			OBJECTS { hwEntityNpsVMName, hwEntityNpsVNFCName, hwEntityNpsRUName, hwEntityNpsErrorDescr }
			STATUS current
			DESCRIPTION 
				"The VM create RU succcess."
			::= { hwEntityNpsTrap 41 }
		
		-- 1.3.6.1.4.1.2011.5.25.219.2.35.42
		hwEntityNpsIpSecRuleFail NOTIFICATION-TYPE
			OBJECTS { hwEntityNpsVMName, hwEntityNpsPortName, hwEntityNpsIPAddress }
			STATUS current
			DESCRIPTION 
				"Setting Security Group Rules Failed."
			::= { hwEntityNpsTrap 42 }
		
		-- 1.3.6.1.4.1.2011.5.25.219.2.35.43
		hwEntityNpsIpSecRuleFailResume NOTIFICATION-TYPE
			OBJECTS { hwEntityNpsVMName, hwEntityNpsPortName, hwEntityNpsIPAddress }
			STATUS current
			DESCRIPTION 
				"Setting Security Group Rules Failed alarm clear."
			::= { hwEntityNpsTrap 43 }
		--1.3.6.1.4.1.2011.5.25.219.2.35.44
		hwEntityNpsBaseLinkSubhealthy NOTIFICATION-TYPE
			OBJECTS { hwEntityNpsLocalVMName, hwEntityNpsRemoteVMName, hwEntityNpsNetworkPlaneID,hwEntityNpsQuality }
			STATUS current
			DESCRIPTION 
				"Base link goes subhealthy."
			::= { hwEntityNpsTrap 44 }
		--1.3.6.1.4.1.2011.5.25.219.2.35.45
		hwEntityNpsBaseLinkSubhealthyResume NOTIFICATION-TYPE
			OBJECTS { hwEntityNpsLocalVMName, hwEntityNpsRemoteVMName, hwEntityNpsNetworkPlaneID,hwEntityNpsQuality }
			STATUS current
			DESCRIPTION 
				"Base link resume from subhealthy."
			::= { hwEntityNpsTrap 45 }


                                 -- 1.3.6.1.4.1.2011.5.25.219.2.36
		hwEntityConfigurationTrap OBJECT IDENTIFIER ::= { hwEntityTraps 36 }

                                     hwEntityConfigurationRollbackRising NOTIFICATION-TYPE
			OBJECTS { hwEntityConfigurationCurrent, hwEntityConfigurationRollbackReason}
			STATUS current
			DESCRIPTION 
				"An alarm was generated when configuration rollback."
			::= { hwEntityConfigurationTrap 1}

 --   1.3.6.1.4.1.2011.5.25.219.2.37 
                 -- 1.3.6.1.4.1.2011.5.25.219.2.37 
                 hwNPDomainDropCauseCntNumabruptlyTrap  OBJECT IDENTIFIER ::= { hwEntityTraps 37 } 
 --   1.3.6.1.4.1.2011.5.25.219.2.37.1 
                 -- 1.3.6.1.4.1.2011.5.25.219.2.37.1 
                 hwNPDomainDropCauseCntNumabruptlyAlarm NOTIFICATION-TYPE
		         OBJECTS { hwEntityPhysicalIndex, entPhysicalName, hwEntityTrapFaultID, hwLpuSlotId, hwLpuFeId, hwDropCauseId, hwHelpinfo} 
                         STATUS current 
                         DESCRIPTION 
                                 "The number of key dropcause count on the NP Chip increases abruptly and exceeds the preset threshold." 
                         ::= { hwNPDomainDropCauseCntNumabruptlyTrap 1 } 
 --   1.3.6.1.4.1.2011.5.25.219.2.37.2 
                 -- 1.3.6.1.4.1.2011.5.25.219.2.37.2  
                 hwNPDomainDropCauseCntNumabruptlyResume NOTIFICATION-TYPE
		         OBJECTS { hwEntityPhysicalIndex, entPhysicalName, hwEntityTrapFaultID, hwLpuSlotId, hwLpuFeId, hwDropCauseId, hwHelpinfo} 
                         STATUS current 
                         DESCRIPTION 
                                 "The number of key dropcause count on the NP Chip return normal ." 
                         ::= { hwNPDomainDropCauseCntNumabruptlyTrap 2 }

--   1.3.6.1.4.1.2011.5.25.219.2.38 
                 -- 1.3.6.1.4.1.2011.5.25.219.2.38 
                 hwNPResourceExcTrap  OBJECT IDENTIFIER ::= { hwEntityTraps 38 } 
 --   1.3.6.1.4.1.2011.5.25.219.2.37.1 
                 -- 1.3.6.1.4.1.2011.5.25.219.2.38.1 
                 hwNPResourceExcAlarm NOTIFICATION-TYPE
		         OBJECTS { hwEntityPhysicalIndex, entPhysicalName, hwEntityTrapFaultID, hwLpuSlotId, hwLpuFeId} 
                         STATUS current 
                         DESCRIPTION 
                                 "NP Resources abnormal." 
                         ::= { hwNPResourceExcTrap 1 } 
 --   1.3.6.1.4.1.2011.5.25.219.2.38.2 
                 -- 1.3.6.1.4.1.2011.5.25.219.2.38.2  
                 hwNPResourceExcResume NOTIFICATION-TYPE
		         OBJECTS { hwEntityPhysicalIndex, entPhysicalName, hwEntityTrapFaultID, hwLpuSlotId, hwLpuFeId} 
                         STATUS current 
                         DESCRIPTION 
                                 "NP resources returns to normal."
                         ::= { hwNPResourceExcTrap 2 } 

--   1.3.6.1.4.1.2011.5.25.219.2.39
               hwEntityFileSystemTrap OBJECT IDENTIFIER ::= { hwEntityTraps 39 }
-- 1.3.6.1.4.1.2011.5.25.219.2.39.1
               -- 1.3.6.1.4.1.2011.5.25.219.2.39.1
                hwEntityFileSystemRebuild NOTIFICATION-TYPE	
               STATUS current 
               DESCRIPTION
               "An alarm was generated when file system rebuild." 
               ::= { hwEntityFileSystemTrap 1} 

-- 1.3.6.1.4.1.2011.5.25.219.2.39.2
		-- 1.3.6.1.4.1.2011.5.25.219.2.39.2
		hwEntityFileSystemAbnormal NOTIFICATION-TYPE
			OBJECTS { hwEntityPhysicalIndex, entPhysicalName, hwEntityTrapFaultID, hwEntityTrapReasonDescr }
			STATUS current
			DESCRIPTION 
				"The filesystem is abnormal."
			::= { hwEntityFileSystemTrap 2 }


-- 1.3.6.1.4.1.2011.5.25.219.2.39.3
		-- 1.3.6.1.4.1.2011.5.25.219.2.39.3
		hwEntityFileSystemFdAlarm NOTIFICATION-TYPE
			OBJECTS { hwEntityPhysicalIndex, entPhysicalName, hwPorcessName }
			STATUS current
			DESCRIPTION 
				"The file handle exceeds the threshold."
			::= { hwEntityFileSystemTrap 3 }

-- 1.3.6.1.4.1.2011.5.25.219.2.39.4
		-- 1.3.6.1.4.1.2011.5.25.219.2.39.4
		hwEntityFileSystemFdResume NOTIFICATION-TYPE
			OBJECTS { hwEntityPhysicalIndex, entPhysicalName, hwPorcessName }
			STATUS current
			DESCRIPTION 
				"The file handle exceeds the threshold alarm cleared."
			::= { hwEntityFileSystemTrap 4 }

-- 1.3.6.1.4.1.2011.5.25.219.2.39.5
		-- 1.3.6.1.4.1.2011.5.25.219.2.39.5
		hwEntityFileSystemAbnormalResume NOTIFICATION-TYPE
			OBJECTS  { hwEntityPhysicalIndex, entPhysicalName, hwEntityTrapFaultID, hwEntityTrapReasonDescr }
			STATUS current
			DESCRIPTION 
				"The filesystem abnormal cleared."
			::= { hwEntityFileSystemTrap 5 }

--   1.3.6.1.4.1.2011.5.25.219.2.40
                 -- 1.3.6.1.4.1.2011.5.25.219.2.40
                 hwEntityHardewareFaultTrap  OBJECT IDENTIFIER ::= { hwEntityTraps 40 } 
 --   1.3.6.1.4.1.2011.5.25.219.2.40.1 
                 -- 1.3.6.1.4.1.2011.5.25.219.2.40.1 
                 hwEntityCODECHardewareFaultAlarm NOTIFICATION-TYPE
                 STATUS current 
                 DESCRIPTION 
                 "CODEC Hardeware Fault." 
                 ::= { hwEntityHardewareFaultTrap 1 } 
 --   1.3.6.1.4.1.2011.5.25.219.2.40.2 
                 -- 1.3.6.1.4.1.2011.5.25.219.2.40.2 
                 hwEntityTPMHardewareFaultAlarm NOTIFICATION-TYPE
                 STATUS current 
                 DESCRIPTION 
                 "TPM Hardeware Fault." 
                 ::= { hwEntityHardewareFaultTrap 2 } 
 --   1.3.6.1.4.1.2011.5.25.219.2.40.3 
                 -- 1.3.6.1.4.1.2011.5.25.219.2.40.3 
                 hwEntityMCUHardewareFaultAlarm NOTIFICATION-TYPE
                 STATUS current 
                 DESCRIPTION 
                 "MCU Hardeware Fault." 
                 ::= { hwEntityHardewareFaultTrap 3 } 

--   1.3.6.1.4.1.2011.5.25.219.2.41
                -- 1.3.6.1.4.1.2011.5.25.219.2.41
                hwInternalProtocolNetworkPortTrap  OBJECT IDENTIFIER ::= { hwEntityTraps 41 } 
--   1.3.6.1.4.1.2011.5.25.219.2.41.1 
                -- 1.3.6.1.4.1.2011.5.25.219.2.41.1 
                hwInternalProtocolNetworkPortFaultAlarm NOTIFICATION-TYPE
                OBJECTS { hwEntityPhysicalIndex, entPhysicalName, hwEntityTrapFaultID }
                STATUS current 
                DESCRIPTION
                "One of the internal protocol network ports failed." 
                ::= { hwInternalProtocolNetworkPortTrap 1 }
--   1.3.6.1.4.1.2011.5.25.219.2.41.2 
                -- 1.3.6.1.4.1.2011.5.25.219.2.41.2
                hwInternalProtocolNetworkPortFaultResume NOTIFICATION-TYPE
                OBJECTS { hwEntityPhysicalIndex, entPhysicalName, hwEntityTrapFaultID }
                STATUS current 
                DESCRIPTION
                "The fault on internal protocol network port is cleared ." 
                ::= { hwInternalProtocolNetworkPortTrap 2 }

--   1.3.6.1.4.1.2011.5.25.219.2.42
                -- 1.3.6.1.4.1.2011.5.25.219.2.42
                hwContainerTrap  OBJECT IDENTIFIER ::= { hwEntityTraps 42 } 
--   1.3.6.1.4.1.2011.5.25.219.2.42.1
		-- 1.3.6.1.4.1.2011.5.25.219.2.42.1
		hwContainerCpuUtilizationRising  NOTIFICATION-TYPE
			OBJECTS { hwEntityPhysicalIndex, entPhysicalName, hwContainerName, hwEntityThresholdType, hwEntityThresholdWarning, hwEntityThresholdCurrent, 
			hwEntityTrapFaultID }
			STATUS current
			DESCRIPTION 
				"Container CPU utilization overrun"
			::= { hwContainerTrap 1 }
			
--   1.3.6.1.4.1.2011.5.25.219.2.42.2
		-- 1.3.6.1.4.1.2011.5.25.219.2.42.2
		hwContainerCpuUtilizationResume NOTIFICATION-TYPE
			OBJECTS { hwEntityPhysicalIndex, entPhysicalName, hwContainerName, hwEntityThresholdType, hwEntityThresholdWarning, hwEntityThresholdCurrent, 
			hwEntityTrapFaultID }
			STATUS current
			DESCRIPTION 
				"Container CPU utilization back to normal level"
			::= { hwContainerTrap 2 }
			
--   1.3.6.1.4.1.2011.5.25.219.2.42.3
		-- 1.3.6.1.4.1.2011.5.25.219.2.42.3
		hwContainerMemUtilizationRising NOTIFICATION-TYPE
			OBJECTS { hwEntityPhysicalIndex, entPhysicalName, hwContainerName, hwEntityThresholdType, hwEntityThresholdWarning, hwEntityThresholdCurrent, 
			hwEntityTrapFaultID }
			STATUS current
			DESCRIPTION 
				"Container mem utilization overrun"
			::= { hwContainerTrap 3 }
			
--   1.3.6.1.4.1.2011.5.25.219.2.42.4
		-- 1.3.6.1.4.1.2011.5.25.219.2.42.4
		hwContainerMemUtilizationResume NOTIFICATION-TYPE
			OBJECTS { hwEntityPhysicalIndex, entPhysicalName, hwContainerName, hwEntityThresholdType, hwEntityThresholdWarning, hwEntityThresholdCurrent, 
			hwEntityTrapFaultID }
			STATUS current
			DESCRIPTION 
				"Container mem utilization back to normal level"
			::= { hwContainerTrap 4 }
			
--   1.3.6.1.4.1.2011.5.25.219.2.42.5
		-- 1.3.6.1.4.1.2011.5.25.219.2.42.5
		hwContainerStorageInsufficient NOTIFICATION-TYPE
			OBJECTS { hwEntityPhysicalIndex, entPhysicalName, hwContainerName, hwEntityThresholdType, hwEntityThresholdWarning, hwEntityThresholdCurrent, 
			hwEntityTrapFaultID }
			STATUS current
			DESCRIPTION 
				"Container storage insufficient"
			::= { hwContainerTrap 5 }
			
--   1.3.6.1.4.1.2011.5.25.219.2.42.6
		-- 1.3.6.1.4.1.2011.5.25.219.2.42.6
		hwContainerStorageInsufficientResume NOTIFICATION-TYPE
			OBJECTS { hwEntityPhysicalIndex, entPhysicalName, hwContainerName, hwEntityThresholdType, hwEntityThresholdWarning, hwEntityThresholdCurrent, 
			hwEntityTrapFaultID }
			STATUS current
			DESCRIPTION 
				"Container storage back to normal level"
			::= { hwContainerTrap 6 }
			
--   1.3.6.1.4.1.2011.5.25.219.2.42.7
		-- 1.3.6.1.4.1.2011.5.25.219.2.42.7
		hwContainerAbnormal NOTIFICATION-TYPE
			OBJECTS { hwEntityPhysicalIndex, entPhysicalName, hwContainerName, hwEntityTrapFaultID }
			STATUS current
			DESCRIPTION 
				"Container run abnormal"
			::= { hwContainerTrap 7 }
--   1.3.6.1.4.1.2011.5.25.219.2.42.8
		-- 1.3.6.1.4.1.2011.5.25.219.2.42.8
		hwContainerAbnormalResume NOTIFICATION-TYPE
			OBJECTS { hwEntityPhysicalIndex, entPhysicalName, hwContainerName, hwEntityTrapFaultID }
			STATUS current
			DESCRIPTION 
				"Container run back to normal"
			::= { hwContainerTrap 8 }
--   1.3.6.1.4.1.2011.5.25.219.2.42.9
		-- 1.3.6.1.4.1.2011.5.25.219.2.42.9
		hwContainerAppAbnormal NOTIFICATION-TYPE
			OBJECTS { hwEntityPhysicalIndex, entPhysicalName, hwContainerName, hwContainerAppName, hwEntityTrapFaultID }
			STATUS current
			DESCRIPTION 
				"App in Container run abnormal"
			::= { hwContainerTrap 9 }
--   1.3.6.1.4.1.2011.5.25.219.2.42.10
		-- 1.3.6.1.4.1.2011.5.25.219.2.42.10
		hwContainerAppAbnormalResume NOTIFICATION-TYPE
			OBJECTS { hwEntityPhysicalIndex, entPhysicalName, hwContainerName, hwContainerAppName, hwEntityTrapFaultID }
			STATUS current
			DESCRIPTION 
				"App in Container back to normal level"
			::= { hwContainerTrap 10 }
--   1.3.6.1.4.1.2011.5.25.219.2.42.11
		-- 1.3.6.1.4.1.2011.5.25.219.2.42.11
		hwFrerLinkPacketLossTrap NOTIFICATION-TYPE
			OBJECTS {hwEntityCpeRemoteStationMAC }
			STATUS current
			DESCRIPTION 
				"Packet loss occurs on the FRER (dual fed and selective receiving) link on the CPE."
			::= { hwContainerTrap 11 }
--   1.3.6.1.4.1.2011.5.25.219.2.42.12
		-- 1.3.6.1.4.1.2011.5.25.219.2.42.12
		hwFrerLinkPacketLossTrapRestore NOTIFICATION-TYPE
			OBJECTS { hwEntityCpeRemoteStationMAC }
			STATUS current
			DESCRIPTION 
				"Cleared the alarm of packet loss on the FRER (dual fed and selective receiving) link on the CPE. "
			::= { hwContainerTrap 12 }
--   1.3.6.1.4.1.2011.5.25.219.2.43
                -- 1.3.6.1.4.1.2011.5.25.219.2.43
                hwCapTableUsageTrap  OBJECT IDENTIFIER ::= { hwEntityTraps 43 } 
--   1.3.6.1.4.1.2011.5.25.219.2.43.1
		-- 1.3.6.1.4.1.2011.5.25.219.2.43.1
		hwSipfpmFlowOverloadTrap  NOTIFICATION-TYPE
			OBJECTS { hwEntityPhysicalIndex, entPhysicalName, hwCapCurSipfpmFlowRate, hwCapUpperSipfpmFlowThreshold, hwCapLowerSipfpmFlowThreshold }
			STATUS current
			DESCRIPTION 
				"The s-ipfpm stream number overload."
			::= { hwCapTableUsageTrap 1 }
--   1.3.6.1.4.1.2011.5.25.219.2.43.2
		-- 1.3.6.1.4.1.2011.5.25.219.2.43.2
		hwSipfpmFlowOverloadRestoreTrap  NOTIFICATION-TYPE
			OBJECTS { hwEntityPhysicalIndex, entPhysicalName, hwCapCurSipfpmFlowRate, hwCapUpperSipfpmFlowThreshold, hwCapLowerSipfpmFlowThreshold }
			STATUS current
			DESCRIPTION 
				"The s-ipfpm stream number overload restore."
			::= { hwCapTableUsageTrap 2 }
		-- 1.3.6.1.4.1.2011.5.25.219.2.43.3
		hwSACSessionOverloadTrap  NOTIFICATION-TYPE
			OBJECTS { hwEntityPhysicalIndex, entPhysicalName, hwCapCurSACSessionRate, hwCapUpperSACSessionThreshold, hwCapLowerSACSessionThreshold }
			STATUS current
			DESCRIPTION 
				"The SAC session usage exceeded the threshold."
			::= { hwCapTableUsageTrap 3 }
		-- 1.3.6.1.4.1.2011.5.25.219.2.43.4
		hwSACSessionOverloadRestoreTrap  NOTIFICATION-TYPE
			OBJECTS { hwEntityPhysicalIndex, entPhysicalName, hwCapCurSACSessionRate, hwCapUpperSACSessionThreshold, hwCapLowerSACSessionThreshold }
			STATUS current
			DESCRIPTION 
				"The SAC session usage was restored to the normal range."
			::= { hwCapTableUsageTrap 4 }
		-- 1.3.6.1.4.1.2011.5.25.219.2.43.5
		hwFwdPacketLoss  NOTIFICATION-TYPE
			OBJECTS { hwEntityPhysicalIndex, entPhysicalName, hwEntityCoreIndex, hwEntityLossType, hwEntityLossCount }
			STATUS current
			DESCRIPTION 
				"Packet loss occurs on the FWD Module."
			::= { hwCapTableUsageTrap 5}

--   1.3.6.1.4.1.2011.5.25.219.2.44
                -- 1.3.6.1.4.1.2011.5.25.219.2.44
                hwSystemTrap OBJECT IDENTIFIER ::= { hwEntityTraps 44 } 
--   1.3.6.1.4.1.2011.5.25.219.2.44.1
		-- 1.3.6.1.4.1.2011.5.25.219.2.44.1
		hwSystemBakeupStartup NOTIFICATION-TYPE
			STATUS current
			DESCRIPTION 
				"The device starts up from the backup software."
			::= { hwSystemTrap 1 }

-- 1.3.6.1.4.1.2011.5.25.219.2.45
		hwLiquidTrap OBJECT IDENTIFIER ::= { hwEntityTraps 45 }
		-- 1.3.6.1.4.1.2011.5.25.219.2.45.1
		hwValveOffline NOTIFICATION-TYPE
			OBJECTS { hwEntityPhysicalIndex, entPhysicalName, hwEntityTrapFaultID }
			STATUS current
			DESCRIPTION 
				"This object indicates that the valve was not present."
			::= { hwLiquidTrap 1 }
		-- 1.3.6.1.4.1.2011.5.25.219.2.45.2
		hwValveOnline NOTIFICATION-TYPE
			OBJECTS { hwEntityPhysicalIndex, entPhysicalName, hwEntityTrapFaultID }
			STATUS current
			DESCRIPTION 
				"This object indicates that the valve was present.."
			::= { hwLiquidTrap 2 }
		-- 1.3.6.1.4.1.2011.5.25.219.2.45.3
		hwValveFault NOTIFICATION-TYPE
			OBJECTS { hwEntityPhysicalIndex, entPhysicalName, hwEntityTrapFaultID } 
			STATUS current
			DESCRIPTION 
				"This object indicates that the valve was fault."
			::= { hwLiquidTrap 3 }
		-- 1.3.6.1.4.1.2011.5.25.219.2.45.4
		hwValveNormal NOTIFICATION-TYPE
			OBJECTS { hwEntityPhysicalIndex, entPhysicalName, hwEntityTrapFaultID } 
			STATUS current
			DESCRIPTION 
				"This object indicates that the valve works normally."
			::= { hwLiquidTrap 4 }
		-- 1.3.6.1.4.1.2011.5.25.219.2.45.5
		hwLiquidSensorOffline NOTIFICATION-TYPE
			OBJECTS { hwEntityPhysicalIndex, entPhysicalName, hwEntityTrapFaultID } 
			STATUS current
			DESCRIPTION 
				"This object indicates that the liquid sensor was not present."
			::= { hwLiquidTrap 5 }
		-- 1.3.6.1.4.1.2011.5.25.219.2.45.6
		hwLiquidSensorOnline NOTIFICATION-TYPE
			OBJECTS { hwEntityPhysicalIndex, entPhysicalName, hwEntityTrapFaultID } 
			STATUS current
			DESCRIPTION 
				"This object indicates that the liquid sensor was present."
			::= { hwLiquidTrap 6 }
		-- 1.3.6.1.4.1.2011.5.25.219.2.45.7
		hwLiquidLeak NOTIFICATION-TYPE
			OBJECTS { hwEntityPhysicalIndex, entPhysicalName, hwEntityTrapFaultID}
			STATUS current
			DESCRIPTION 
				"This object indicates that the board leakage."
			::= { hwLiquidTrap 7 }
		-- 1.3.6.1.4.1.2011.5.25.219.2.45.8
		hwNoLeak NOTIFICATION-TYPE
			OBJECTS { hwEntityPhysicalIndex, entPhysicalName, hwEntityTrapFaultID }
			STATUS current
			DESCRIPTION 
				"This object indicates that the board liquid system normally."
			::= { hwLiquidTrap 8 }
		-- 1.3.6.1.4.1.2011.5.25.219.2.45.9
		hwValveCommFault NOTIFICATION-TYPE
			OBJECTS { hwEntityPhysicalIndex, entPhysicalName, hwEntityTrapFaultID } 
			STATUS current
			DESCRIPTION 
				"This object indicates that the valve was communicatie fault."
			::= { hwLiquidTrap 9 }
		-- 1.3.6.1.4.1.2011.5.25.219.2.45.10
		hwValveCommNormal NOTIFICATION-TYPE
			OBJECTS { hwEntityPhysicalIndex, entPhysicalName, hwEntityTrapFaultID } 
			STATUS current
			DESCRIPTION 
				"This object indicates that the valve works normally."
			::= { hwLiquidTrap 10 }
		-- 1.3.6.1.4.1.2011.5.25.219.2.45.11
		hwValveInspectFault NOTIFICATION-TYPE
			OBJECTS { hwEntityPhysicalIndex, entPhysicalName, hwEntityTrapFaultID } 
			STATUS current
			DESCRIPTION 
				"This object indicates that the valve inspection is not executed."
			::= { hwLiquidTrap 11 }
		-- 1.3.6.1.4.1.2011.5.25.219.2.45.12
		hwValveInspectNormal NOTIFICATION-TYPE
			OBJECTS { hwEntityPhysicalIndex, entPhysicalName, hwEntityTrapFaultID } 
			STATUS current
			DESCRIPTION 
				"This object indicates that the valve inspection completed."
			::= { hwLiquidTrap 12 }
		-- 1.3.6.1.4.1.2011.5.25.219.2.45.13
		hwChannelFault NOTIFICATION-TYPE
			OBJECTS { hwEntityPhysicalIndex, entPhysicalName, hwEntityTrapFaultID } 
			STATUS current
			DESCRIPTION 
				"This object indicates that the liquid valve channel was fault."
			::= { hwLiquidTrap 13 }
		-- 1.3.6.1.4.1.2011.5.25.219.2.45.14
		hwChannelNormal NOTIFICATION-TYPE
			OBJECTS { hwEntityPhysicalIndex, entPhysicalName, hwEntityTrapFaultID } 
			STATUS current
			DESCRIPTION 
				"This object indicates that the liquid valve channel works normally."
			::= { hwLiquidTrap 14 }

--   1.3.6.1.4.1.2011.5.25.219.3
-- 1.3.6.1.4.1.2011.5.25.219.3
		-- 1.3.6.1.4.1.2011.5.25.219.3
		hwEntityTrapConformance OBJECT IDENTIFIER ::= { hwEntityTrapMIB 3 }

		
--  1.3.6.1.4.1.2011.5.25.219.3.1
		-- 1.3.6.1.4.1.2011.5.25.219.3.1
		hwEntityTrapCompliances OBJECT IDENTIFIER ::= { hwEntityTrapConformance 1 }

		
--   this module
-- 1.3.6.1.4.1.2011.5.25.219.3.1.1
-- this module
		-- 1.3.6.1.4.1.2011.5.25.219.3.1.1
		hwEntityTrapCompliance MODULE-COMPLIANCE
			STATUS current
			DESCRIPTION 
				"Compliance statement for agents that provide full support for 
				hwBaseTrapMIB."
			MODULE -- this module
				MANDATORY-GROUPS { hwEntityObjectGroup }
			::= { hwEntityTrapCompliances 1 }

		
--  1.3.6.1.4.1.2011.5.25.219.3.2
		-- 1.3.6.1.4.1.2011.5.25.219.3.2
		hwEntityTrapGroups OBJECT IDENTIFIER ::= { hwEntityTrapConformance 2 }

		
--  1.3.6.1.4.1.2011.5.25.219.3.2.1
		-- 1.3.6.1.4.1.2011.5.25.219.3.2.1
		hwEntityObjectGroup OBJECT-GROUP
			OBJECTS { hwEntityPhysicalIndex, hwEntityTrapEntType, hwEntityTrapFaultID, hwEntityCommunicateType, hwEntityThresholdType, 
				hwEntityThresholdValue, hwEntityThresholdCurrent, hwEntityThresholdCritical, hwEntityThresholdWarning, hwUserDefAlarmName, 
				hwUserDefChannel, hwDeviceMasterESN, hwSoftwareVersion, hwStartupSoftwareFileName, hwStorageDevName, hwPortDownReason, 
                                hwEntityTrapRelativeResource, hwEntityTrapReasonDescr,hwUsbOperType, hwOpticalVendorName, hwOpticalVendorSN, hwMasterOpUser, hwAPAdminIP, hwAPID, hwOperation, hwReason,
				hwBoardID, hwCapCPUThresholdType, hwCapCPUThresholdValue, hwCapCPUThresholdCurrent, hwSyslogModuleName, 
				hwSyslogSeverityLevel, hwSyslogBrief, hwSyslogDescription, hwSyslogTimeStamp, hwEntityNpsVMName, 
				hwEntityNpsVMID, hwEntityNpsPhyVMID, hwEntityNpsErrorCode, hwEntityNpsErrorDescr, hwEntityNpsPort, 
				hwEntityNpsPortName, hwEntityNpsIPAddress, hwEntityNpsPatchName, hwEntityNpsPatchVersion, hwEntityNpsCertName, 
				hwEntityNpsCertType, hwEntityNpsCertRemainDays, hwEntityNpsCertValidBeginTime, hwEntityNpsCertValidEndTime, hwEntityNpsPartitionName, 
				hwEntityNpsPartitionUsage, hwEntityNpsPartitionUsageThreshold, hwEntityNpsPartitionAvailableSpace, hwEntityNpsPartitionCapacityThreshold, hwEntityNpsRUName, 
				hwEntityNpsVNFCName, hwEntityNpsVNFCType, hwEntityNpsAPPType, hwEntityNpsSoftwareVersionType, hwEntityNpsSoftwareVersionID, 
				hwEntityNpsLocalVMName, hwEntityNpsRemoteVMName, hwEntityNpsNetworkPlaneID, hwEntityNpsNetworkErrorThreshold, hwEntityNpsDeviceID, 
				hwEntityNpsDriverVendor, hwEntityNpsDriverType,hwEntityNpsQuality,hwLicenseRemainTime, hwVirtualLicenseItemName, hwCapMemType, hwCapMemThresholdValue, hwCapMemThresholdCurrent,
				hwCapSingleCoreThresholdCurrent, hwCapSingleCoreIndex, hwCapSingleCoreThresholdValue, hwCapCurSipfpmFlowRate, hwCapUpperSipfpmFlowThreshold, hwCapLowerSipfpmFlowThreshold, hwEntityCpeRemoteStationMAC,
				hwCapCurSACSessionRate, hwCapUpperSACSessionThreshold, hwCapLowerSACSessionThreshold, hwAvailableMemory, hwAvailableMemoryThreshold }
			STATUS current
			DESCRIPTION 
				"Group for base trap objects."
			::= { hwEntityTrapGroups 1 }

		
--  1.3.6.1.4.1.2011.5.25.219.3.2.2
		-- 1.3.6.1.4.1.2011.5.25.219.3.2.2
		hwEntityTrapGroup NOTIFICATION-GROUP
			NOTIFICATIONS { hwBoardLicenseActSuccess, hwBoardLicenseActFail, hwChassisRemove, hwChassisInsert, hwChassisFail, hwChassisFailResume, hwChassisInvalid, 
				hwChassisInvalidResume, hwBoardRemove, hwBoardInsert, hwBoardFail, hwBoardFailResume, hwForwardEngineFail,  hwForwardEngineFailResume, hwForwardEngineInvalid, hwForwardEngineInvalidResume,hwForwardEngineModelFail, hwForwardEngineModelFailResume, hwForwardEnginePortFail, hwForwardEnginePortFailResume, hwDeviceRebootTrap, 
				hwBoardInvalid, hwBoardInvalidResume, hwBoardLeaveMaster, hwBoardBecomeMaster, hwCardRemove, hwChassisMinorAlarm, hwChassisMinorAlarmResume, hwSlicePowerFail, hwWarmBackFail, hwChassisPowerChanged,
				hwCardInsert, hwCardFail, hwCardFailResume, hwCardInvalid, hwCardInvalidResume, hwCardResExceed, hwCardResExceedResume,
				hwOpticalRemove, hwOpticalInsert, hwOpticalFail, hwOpticalFailResume, hwOpticalInvalid, 
				hwOpticalInvalidResume, hwGpsModuleRemove,hwGpsModuleInsert,hwOptCfgNotMatch,hwOptCfgNotMatchResume,hwOpticalBiasCurrentAlarm,hwOpticalBiasCurrentAlarmResume ,hwPowerRemove, hwPowerInsert, hwPowerFail, hwPowerFailResume, 
				hwPowerInvalid, hwPowerInvalidResume, hwPowerUnusable, hwPowerUnusableResume, hwFanRemove, 
				hwFanInsert, hwFanFail, hwFanFailResume, hwFanInvalid, hwFanInvalidResume, hwFanMinorAlarm, hwFanMinorAlarmResume,
				hwFanUnusable, hwFanUnusableResume, hwLcdRemove, hwLcdInsert, hwLcdInvalid, 
				hwLcdInvalidResume, hwLcdUnusable, hwLcdUnusableResume, hwCmuRemove, hwCmuInsert, 
				hwCmuInvalid, hwCmuInvalidResume, hwCmuUnusable, hwCmuUnusableResume, hwCmuFail, hwCmuFailResume, hwCommunicateError, 
				hwCommunicateResume, hwTempAlarm, hwTempResume, hwHumidityAlarm, hwHumidityResume, 
				hwVoltAlarm, hwVoltResume, hwGateAlarm, hwGateResume, hwFogAlarm, 
				hwFogResume, hwUnstableAlarm, hwUnstableResume, hwBrdTempAlarm, hwBrdTempResume, 
				hwBrdTempFatalAlarm, hwBrdTempFatalResume, hwPowerFailureAlarm, hwPowerFailureResume, hwIOSwitchOneAlarm, 
				hwIOSwitchOneAlarmResume, hwIOSwitchTwoAlarm, hwIOSwitchTwoAlarmResume, hwIOSwitchThreeAlarm, hwIOSwitchThreeAlarmResume, hwIOSwitchAlarm, hwIOSwitchAlarmResume,
				hwEntityDyingGaspEvent, hwSystemConfigError, hwSystemConfigResume, hwPortDown, 
				hwPortUp, hwPortNoSupportOETrap, hwPortRemove, hwPortInsert,hwPortOpticalPositionInvalid,hwPortOpticalPositionValid, hwUserDefAlarm, hwUserDefResume, hwPeerDevPnPTrunkAggregationFailure, hwEsnMismatch, hwMacNumMismatch, hwAvaMemInsufficient, hwAvaMemInsufficientResume, hwCPUUtilizationRising, hwCPUUtilizationResume, hwCpuFail, hwCpuFailResume,     
				hwUSBUnidentifiedResume, hwUSBUnidentified,
				hwMemUtilizationRising, hwMemUtilizationResume, hwStorageDevRemove, hwStorageDevInsert, hwSystemRollback, hwVirtualAccessDrvConfigError,
				hwUpMicroSwitchOpen, hwUpMicroSwitchClose, hwDownMicroSwitchOpen, hwDownMicroSwitchClose, hwBoardPowerOff, hwOpticalPowerAlarm, 
				hwOpticalPowerAlarmResume,hwUSBInsert,hwPppLoopbackDetect,hwUSBRemove,hwPppLoopbackDetResume,hwFileErrorResume,hwFileError,
				hwPmuRemove,hwPmuInsert,hwPmuFail,hwPmuFailResume,hwPmuInvalid,hwPmuInvalidResume,hwRATEOFTRAFFICRising,hwBatteryFull, hwUpsFaultTrap, hwUpsFaultResume, hwUpsPowerLow, hwUpsPowerFull, hwRATEOFTRAFFICResume,
				hwThreadFaultIsolate, hwOpticalUnAuthorized, hwOpticalUnAuthorizedResume, hwLaserNoFited, hwLaserNoFitedResume,
				hwOpticalTunableNotMatch, hwOpticalTunableNotMatchResume ,hwBandwidthOfAllCardsExceedsThreshold ,hwUsbStatusChg,
				hwBoardResetByCmd, hwBoardResetByCmdResume, hwCardResetByCmd, hwDiskUtilizationResume, hwDiskUtilizationRising, hwCardResetByCmdResume, hwBoardHeartbeatTimeout, 
				hwBoardHeartbeatResume, hwBandwidthOfAllCardsExceedsThresholdAlarm,hwBandwidthOfAllCardsExceedsThresholdResume,hwBandwidthOfAllBoardsExceedsThresholdAlarm, hwBandwidthOfAllBoardsExceedsThresholdAlarmResume,
				hwBandwidthOfAllCardsExceedsThresholdFatalAlarm, hwBandwidthOfAllCardsExceedsThresholdFatalResume,hwPinchCardReset,hwPinchCardResetResume,hwVMResInconsist,hwVMResInconsistResume, hwNeedModifyCfgTrap, hwCardBandwidthModeChange, hwCardSplitChange,
				hwBoardWarning, hwBoardWarningResume, hwBoardPortsConflict, hwDataplaneCpuOverloadAlarm, hwDataplaneCpuOverloadResume, hwInsSpaceLackAlarm, hwInsSpaceLackResume, hwVfpSysCheckErr, hwVfpSysCheckErrResume,hwBoardlowmemoryoverload,hwBoardlowmemoryoverloadResume, hwBiosOrBootloaderPwdError, hwBiosOrBootloaderPwdErrorResume,hwBootloaderPwdEmpty, hwBootloaderPwdEmptyResume,
                                hwCapCPUUtilizationResume, hwCapCPUUtilizationRising, hwCardInconsistent, hwBoardAdd, hwBoardDelete, hwRTULicenseActSuccess, hwSMSReboot, hwPduNotPresent, hwPduPresent, hwPduCommLost, hwPduCommLostResume, hwPduDmuHardwareFault, hwPduDmuHardwareFaultResume, hwPduDMUAutoUpgradeFail, hwPduDMUAutoUpgradeFailResume, hwPduDacsHardwareFault, hwPduDacsHardwareFaultResume, 
				hwPduDacsTempAlarm, hwPduDacsTempAlarmResume, hwPduDacsI2CChannelFault, hwPduDacsI2CChannelFaultResume, hwReportSyslogInfo,
				hwEntityNpsPatchInstallFail, hwEntityNpsPatchInstallFailResume, hwEntityNpsPatchPacketError, 
				hwEntityNpsPatchPacketErrorResume, hwEntityNpsSysConfigError, hwEntityNpsSysConfigErrorResume, hwEntityNpsSslCertInvalidEarlyWarning, hwEntityNpsSslCertInvalidEarlyResume, 
				hwEntityNpsSslCertInvalid, hwEntityNpsSslCertInvalidResume, hwEntityNpsDiskPartitionUsageExceedingThreshold, hwEntityNpsDiskPartitionUsageExceedingThresholdResume, hwEntityNpsDiskPartitionUnavailable, 
				hwEntityNpsDiskPartitionUnavailableResume, hwEntityNpsDiskPartitionSpaceInsufficient, hwEntityNpsDiskPartitionSpaceInsufficientResume, hwEntityNpsExecutableFilesIncomplete, hwEntityNpsExecutableFilesIncompleteResume, 
				hwEntityNpsSoftwareIntegrityError, hwEntityNpsSoftwareIntegrityErrorResume, hwEntityNpsOMUSyncFail, hwEntityNpsOMUSyncFailResume, hwEntityNpsVMDiskUnavailable, 
				hwEntityNpsVMDiskUnavailableResume, hwEntityNpsDatabaseRestoreFail, hwEntityNpsSSLCertExpired, hwEntityNpsSSLCertExpiredEarlyWarning, hwEntityNpsVMResInconsist, 
				hwEntityNpsVMResInconsistResume, hwEntityNpsVmFault, hwEntityNpsVmFaultResume, hwEntityNpsVNFMConnectFault, hwEntityNpsVNFMConnectResume, 
				hwEntityNpsFabricOamPlaneDown, hwEntityNpsFabricOamPlaneDownResume, hwEntityNpsFabricLinkSubhealthy, hwEntityNpsFabricLinkSubhealthyResume, hwEntityNpsDriverTypeMismatch, 
				hwEntityNpsDriverTypeMismatchResume, hwEntityNpsRuCreateFail, hwEntityNpsRuCreateFailResume, hwEntityNpsIpSecRuleFail, hwBoardUpCoverResume, hwBoardUpCoverAlarm, hwEntityNpsIpSecRuleFailResume, hwAllLpuSfuFail, hwAllLpuSfuFailResume,hwEntityNpsBaseLinkSubhealthy,hwEntityNpsBaseLinkSubhealthyResume,
				hwVirtualLicenseExpire, hwVirtualLicenseNearDeadline, hwNPDomainDropCauseCntNumabruptlyAlarm, hwNPDomainDropCauseCntNumabruptlyResume,hwNPResourceExcAlarm,hwNPResourceExcResume,hwEntityFileSystemRebuild,hwEntityFileSystemAbnormal,hwEntityFileSystemAbnormalResume,hwEntityCODECHardewareFaultAlarm,hwEntityTPMHardewareFaultAlarm,hwEntityMCUHardewareFaultAlarm, hwInternalProtocolNetworkPortFaultAlarm, hwInternalProtocolNetworkPortFaultResume, 
                hwBatteryGroupFault, hwBatteryGroupFaultResume, hwBatteryFault, hwBatteryFaultResume, hwBatteryMinorFault, hwBatteryMinorFaultResume, hwCertExpired, hwCertExpiredResume, hwCrlInvalid, hwCrlInvalidResume, hwTmStatusChangeAlarm, hwTmStatusChangeAlarmResume, hwCapMemUtilizationRising, hwCapMemUtilizationResume, hwCapSingleCoreCPUUtilizationRising, hwCapSingleCoreCPUUtilizationResume,hwVirtualLicenseNearDeadlineResume, hwSipfpmFlowOverloadTrap, hwSipfpmFlowOverloadRestoreTrap, hwFrerLinkPacketLossTrap, hwFrerLinkPacketLossTrapRestore,
				hwSACSessionOverloadTrap, hwSACSessionOverloadRestoreTrap, hwSystemBakeupStartup, hwBoardUpCoverStackAlarm, hwBoardUpCoverStackResume}
			STATUS current
			DESCRIPTION 
				"Group for all base traps."
			::= { hwEntityTrapGroups 2 }

		
	
	END

--
-- HUAWEI-ENTITY-TRAP-MIB.my
--
